SelfBilledInvoice-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, TaxPointDate, InvoiceTypeCode, 
    Note, DocumentCurrencyCode, TaxCurrencyCode, PricingCurrencyCode, 
    PaymentCurrencyCode, PaymentAlternativeCurrencyCode, AccountingCostCode, 
    AccountingCost, LineCountNumeric
    FROM CommonBasicComponents-2
    InvoicePeriod, OrderReference, BillingReference, 
    ContractDocumentReference, DespatchDocumentReference, 
    ReceiptDocumentReference, StatementDocumentReference, 
    OriginatorDocumentReference, AdditionalDocumentReference, Signature-1, 
    AccountingCustomerParty, AccountingSupplierParty, BuyerCustomerParty, 
    SellerSupplierParty, PayeeParty, TaxRepresentativeParty, Delivery, 
    DeliveryTerms, PaymentMeans, PaymentTerms, PrepaidPayment, 
    AllowanceCharge, TaxExchangeRate, PricingExchangeRate, 
    PaymentExchangeRate, PaymentAlternativeExchangeRate, TaxTotal, 
    LegalMonetaryTotal, InvoiceLine
    FROM CommonAggregateComponents-2;

SelfBilledInvoice ::= SelfBilledInvoiceType

SelfBilledInvoiceType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    taxPointDate TaxPointDate OPTIONAL,
    invoiceTypeCode InvoiceTypeCode OPTIONAL,
    note-list  SEQUENCE OF note Note,
    documentCurrencyCode DocumentCurrencyCode OPTIONAL,
    taxCurrencyCode TaxCurrencyCode OPTIONAL,
    pricingCurrencyCode PricingCurrencyCode OPTIONAL,
    paymentCurrencyCode PaymentCurrencyCode OPTIONAL,
    paymentAlternativeCurrencyCode PaymentAlternativeCurrencyCode OPTIONAL,
    accountingCostCode AccountingCostCode OPTIONAL,
    accountingCost AccountingCost OPTIONAL,
    lineCountNumeric LineCountNumeric OPTIONAL,
    invoicePeriod-list SEQUENCE OF invoicePeriod InvoicePeriod,
    orderReference OrderReference OPTIONAL,
    billingReference-list SEQUENCE OF billingReference BillingReference,
    contractDocumentReference-list SEQUENCE OF contractDocumentReference 
	ContractDocumentReference,
    despatchDocumentReference-list SEQUENCE OF despatchDocumentReference 
	DespatchDocumentReference,
    receiptDocumentReference-list SEQUENCE OF receiptDocumentReference 
	ReceiptDocumentReference,
    statementDocumentReference-list SEQUENCE OF statementDocumentReference 
	StatementDocumentReference,
    originatorDocumentReference-list SEQUENCE OF originatorDocumentReference 
	OriginatorDocumentReference,
    additionalDocumentReference-list SEQUENCE OF additionalDocumentReference 
	AdditionalDocumentReference,
    signature-list SEQUENCE OF signature Signature-1,
    accountingCustomerParty AccountingCustomerParty,
    accountingSupplierParty AccountingSupplierParty,
    buyerCustomerParty BuyerCustomerParty OPTIONAL,
    sellerSupplierParty SellerSupplierParty OPTIONAL,
    payeeParty PayeeParty OPTIONAL,
    taxRepresentativeParty TaxRepresentativeParty OPTIONAL,
    delivery-list SEQUENCE OF delivery Delivery,
    deliveryTerms-list SEQUENCE OF deliveryTerms DeliveryTerms,
    paymentMeans PaymentMeans OPTIONAL,
    paymentTerms-list SEQUENCE OF paymentTerms PaymentTerms,
    prepaidPayment-list SEQUENCE OF prepaidPayment PrepaidPayment,
    allowanceCharge-list SEQUENCE OF allowanceCharge AllowanceCharge,
    taxExchangeRate TaxExchangeRate OPTIONAL,
    pricingExchangeRate PricingExchangeRate OPTIONAL,
    paymentExchangeRate PaymentExchangeRate OPTIONAL,
    paymentAlternativeExchangeRate PaymentAlternativeExchangeRate OPTIONAL,
    taxTotal-list SEQUENCE OF taxTotal TaxTotal,
    legalMonetaryTotal LegalMonetaryTotal,
    invoiceLine-list SEQUENCE (SIZE(1..MAX)) OF invoiceLine InvoiceLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:SelfBilledInvoice-2"
	PREFIX "ns46"
    NAMESPACE SelfBilledInvoiceType.uBLExtensions
	AS "urn:oasis:names:specification:ubl:schema:xsd:CommonExtensionComponents-2"
	    PREFIX "ext"
    NAMESPACE SelfBilledInvoiceType.uBLVersionID, 
	SelfBilledInvoiceType.customizationID, 
	SelfBilledInvoiceType.profileID, 
	SelfBilledInvoiceType.profileExecutionID, SelfBilledInvoiceType.iD, 
	SelfBilledInvoiceType.copyIndicator, SelfBilledInvoiceType.uUID, 
	SelfBilledInvoiceType.issueDate, SelfBilledInvoiceType.issueTime, 
	SelfBilledInvoiceType.taxPointDate, 
	SelfBilledInvoiceType.invoiceTypeCode, 
	SelfBilledInvoiceType.note-list.note, 
	SelfBilledInvoiceType.documentCurrencyCode, 
	SelfBilledInvoiceType.taxCurrencyCode, 
	SelfBilledInvoiceType.pricingCurrencyCode, 
	SelfBilledInvoiceType.paymentCurrencyCode, 
	SelfBilledInvoiceType.paymentAlternativeCurrencyCode, 
	SelfBilledInvoiceType.accountingCostCode, 
	SelfBilledInvoiceType.accountingCost, 
	SelfBilledInvoiceType.lineCountNumeric
	AS "urn:oasis:names:specification:ubl:schema:xsd:CommonBasicComponents-2"
	    PREFIX "cbc"
    NAMESPACE SelfBilledInvoiceType.invoicePeriod-list.invoicePeriod, 
	SelfBilledInvoiceType.orderReference, 
	SelfBilledInvoiceType.billingReference-list.billingReference, 
	SelfBilledInvoiceType.contractDocumentReference-list.contractDocumentReference,
	SelfBilledInvoiceType.despatchDocumentReference-list.despatchDocumentReference,
	SelfBilledInvoiceType.receiptDocumentReference-list.receiptDocumentReference,
	SelfBilledInvoiceType.statementDocumentReference-list.statementDocumentReference,
	SelfBilledInvoiceType.originatorDocumentReference-list.originatorDocumentReference,
	SelfBilledInvoiceType.additionalDocumentReference-list.additionalDocumentReference,
	SelfBilledInvoiceType.signature-list.signature, 
	SelfBilledInvoiceType.accountingCustomerParty, 
	SelfBilledInvoiceType.accountingSupplierParty, 
	SelfBilledInvoiceType.buyerCustomerParty, 
	SelfBilledInvoiceType.sellerSupplierParty, 
	SelfBilledInvoiceType.payeeParty, 
	SelfBilledInvoiceType.taxRepresentativeParty, 
	SelfBilledInvoiceType.delivery-list.delivery, 
	SelfBilledInvoiceType.deliveryTerms-list.deliveryTerms, 
	SelfBilledInvoiceType.paymentMeans, 
	SelfBilledInvoiceType.paymentTerms-list.paymentTerms, 
	SelfBilledInvoiceType.prepaidPayment-list.prepaidPayment, 
	SelfBilledInvoiceType.allowanceCharge-list.allowanceCharge, 
	SelfBilledInvoiceType.taxExchangeRate, 
	SelfBilledInvoiceType.pricingExchangeRate, 
	SelfBilledInvoiceType.paymentExchangeRate, 
	SelfBilledInvoiceType.paymentAlternativeExchangeRate, 
	SelfBilledInvoiceType.taxTotal-list.taxTotal, 
	SelfBilledInvoiceType.legalMonetaryTotal, 
	SelfBilledInvoiceType.invoiceLine-list.invoiceLine
	AS "urn:oasis:names:specification:ubl:schema:xsd:CommonAggregateComponents-2"
	    PREFIX "cac"
    NAME SelfBilledInvoiceType.uBLExtensions, 
	SelfBilledInvoiceType.uBLVersionID, 
	SelfBilledInvoiceType.customizationID, 
	SelfBilledInvoiceType.profileID, 
	SelfBilledInvoiceType.profileExecutionID, SelfBilledInvoiceType.iD, 
	SelfBilledInvoiceType.copyIndicator, SelfBilledInvoiceType.uUID, 
	SelfBilledInvoiceType.issueDate, SelfBilledInvoiceType.issueTime, 
	SelfBilledInvoiceType.taxPointDate, 
	SelfBilledInvoiceType.invoiceTypeCode, 
	SelfBilledInvoiceType.note-list.note, 
	SelfBilledInvoiceType.documentCurrencyCode, 
	SelfBilledInvoiceType.taxCurrencyCode, 
	SelfBilledInvoiceType.pricingCurrencyCode, 
	SelfBilledInvoiceType.paymentCurrencyCode, 
	SelfBilledInvoiceType.paymentAlternativeCurrencyCode, 
	SelfBilledInvoiceType.accountingCostCode, 
	SelfBilledInvoiceType.accountingCost, 
	SelfBilledInvoiceType.lineCountNumeric, 
	SelfBilledInvoiceType.invoicePeriod-list.invoicePeriod, 
	SelfBilledInvoiceType.orderReference, 
	SelfBilledInvoiceType.billingReference-list.billingReference, 
	SelfBilledInvoiceType.contractDocumentReference-list.contractDocumentReference,
	SelfBilledInvoiceType.despatchDocumentReference-list.despatchDocumentReference,
	SelfBilledInvoiceType.receiptDocumentReference-list.receiptDocumentReference,
	SelfBilledInvoiceType.statementDocumentReference-list.statementDocumentReference,
	SelfBilledInvoiceType.originatorDocumentReference-list.originatorDocumentReference,
	SelfBilledInvoiceType.additionalDocumentReference-list.additionalDocumentReference,
	SelfBilledInvoiceType.signature-list.signature, 
	SelfBilledInvoiceType.accountingCustomerParty, 
	SelfBilledInvoiceType.accountingSupplierParty, 
	SelfBilledInvoiceType.buyerCustomerParty, 
	SelfBilledInvoiceType.sellerSupplierParty, 
	SelfBilledInvoiceType.payeeParty, 
	SelfBilledInvoiceType.taxRepresentativeParty, 
	SelfBilledInvoiceType.delivery-list.delivery, 
	SelfBilledInvoiceType.deliveryTerms-list.deliveryTerms, 
	SelfBilledInvoiceType.paymentMeans, 
	SelfBilledInvoiceType.paymentTerms-list.paymentTerms, 
	SelfBilledInvoiceType.prepaidPayment-list.prepaidPayment, 
	SelfBilledInvoiceType.allowanceCharge-list.allowanceCharge, 
	SelfBilledInvoiceType.taxExchangeRate, 
	SelfBilledInvoiceType.pricingExchangeRate, 
	SelfBilledInvoiceType.paymentExchangeRate, 
	SelfBilledInvoiceType.paymentAlternativeExchangeRate, 
	SelfBilledInvoiceType.taxTotal-list.taxTotal, 
	SelfBilledInvoiceType.legalMonetaryTotal, 
	SelfBilledInvoiceType.invoiceLine-list.invoiceLine AS CAPITALIZED
    UNTAGGED SEQUENCE OF
END
