AwardedNotification-2
DEFINITIONS AUTOMATIC TAGS ::=
BEGIN
IMPORTS 
    UBLExtensions
    FROM CommonExtensionComponents-2
    UBLVersionID, CustomizationID, ProfileID, ProfileExecutionID, ID-1, 
    CopyIndicator, UUID, ContractFolderID, IssueDate, IssueTime, ContractName,
    Note
    FROM CommonBasicComponents-2
    SenderParty, ReceiverParty, MinutesDocumentReference, 
    AdditionalDocumentReference, TenderResult, FinalFinancialGuarantee, 
    Signature-1
    FROM CommonAggregateComponents-2;

AwardedNotification ::= AwardedNotificationType

AwardedNotificationType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    contractFolderID ContractFolderID,
    issueDate  IssueDate,
    issueTime  IssueTime OPTIONAL,
    contractName ContractName OPTIONAL,
    note-list  SEQUENCE OF note Note,
    senderParty SenderParty,
    receiverParty ReceiverParty,
    minutesDocumentReference MinutesDocumentReference OPTIONAL,
    additionalDocumentReference-list SEQUENCE OF additionalDocumentReference 
	AdditionalDocumentReference,
    tenderResult-list SEQUENCE (SIZE(1..MAX)) OF tenderResult TenderResult,
    finalFinancialGuarantee-list SEQUENCE OF finalFinancialGuarantee 
	FinalFinancialGuarantee,
    signature-list SEQUENCE OF signature Signature-1
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:AwardedNotification-2"
	PREFIX "ns2"
    NAMESPACE AwardedNotificationType.uBLExtensions
	AS "urn:oasis:names:specification:ubl:schema:xsd:CommonExtensionComponents-2"
	    PREFIX "ext"
    NAMESPACE AwardedNotificationType.uBLVersionID, 
	AwardedNotificationType.customizationID, 
	AwardedNotificationType.profileID, 
	AwardedNotificationType.profileExecutionID, 
	AwardedNotificationType.iD, AwardedNotificationType.copyIndicator, 
	AwardedNotificationType.uUID, 
	AwardedNotificationType.contractFolderID, 
	AwardedNotificationType.issueDate, AwardedNotificationType.issueTime, 
	AwardedNotificationType.contractName, 
	AwardedNotificationType.note-list.note
	AS "urn:oasis:names:specification:ubl:schema:xsd:CommonBasicComponents-2"
	    PREFIX "cbc"
    NAMESPACE AwardedNotificationType.senderParty, 
	AwardedNotificationType.receiverParty, 
	AwardedNotificationType.minutesDocumentReference, 
	AwardedNotificationType.additionalDocumentReference-list.additionalDocumentReference,
	AwardedNotificationType.tenderResult-list.tenderResult, 
	AwardedNotificationType.finalFinancialGuarantee-list.finalFinancialGuarantee,
	AwardedNotificationType.signature-list.signature
	AS "urn:oasis:names:specification:ubl:schema:xsd:CommonAggregateComponents-2"
	    PREFIX "cac"
    NAME AwardedNotificationType.uBLExtensions, 
	AwardedNotificationType.uBLVersionID, 
	AwardedNotificationType.customizationID, 
	AwardedNotificationType.profileID, 
	AwardedNotificationType.profileExecutionID, 
	AwardedNotificationType.iD, AwardedNotificationType.copyIndicator, 
	AwardedNotificationType.uUID, 
	AwardedNotificationType.contractFolderID, 
	AwardedNotificationType.issueDate, AwardedNotificationType.issueTime, 
	AwardedNotificationType.contractName, 
	AwardedNotificationType.note-list.note, 
	AwardedNotificationType.senderParty, 
	AwardedNotificationType.receiverParty, 
	AwardedNotificationType.minutesDocumentReference, 
	AwardedNotificationType.additionalDocumentReference-list.additionalDocumentReference,
	AwardedNotificationType.tenderResult-list.tenderResult, 
	AwardedNotificationType.finalFinancialGuarantee-list.finalFinancialGuarantee,
	AwardedNotificationType.signature-list.signature AS CAPITALIZED
    UNTAGGED SEQUENCE OF
END
