GoodsItemItinerary-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, VersionID, 
    TransportExecutionPlanReferenceID
    FROM CommonBasicComponents-2
    Signature-1, SenderParty, ReceiverParty, ReferencedGoodsItem, 
    ReferencedPackage, ReferencedTransportEquipment, TransportationSegment
    FROM CommonAggregateComponents-2;

GoodsItemItinerary ::= GoodsItemItineraryType

GoodsItemItineraryType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    issueDate  IssueDate OPTIONAL,
    issueTime  IssueTime OPTIONAL,
    note-list  SEQUENCE OF note Note,
    versionID  VersionID,
    transportExecutionPlanReferenceID TransportExecutionPlanReferenceID,
    signature-list SEQUENCE OF signature Signature-1,
    senderParty SenderParty OPTIONAL,
    receiverParty ReceiverParty OPTIONAL,
    referencedGoodsItem-list SEQUENCE OF referencedGoodsItem 
	ReferencedGoodsItem,
    referencedPackage-list SEQUENCE OF referencedPackage ReferencedPackage,
    referencedTransportEquipment-list SEQUENCE OF referencedTransportEquipment
	ReferencedTransportEquipment,
    transportationSegment-list SEQUENCE (SIZE(1..MAX)) OF 
	transportationSegment TransportationSegment
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:GoodsItemItinerary-2"
	PREFIX "ns24"
    NAMESPACE GoodsItemItineraryType.uBLExtensions
	AS "urn:oasis:names:specification:ubl:schema:xsd:CommonExtensionComponents-2"
	    PREFIX "ext"
    NAMESPACE GoodsItemItineraryType.uBLVersionID, 
	GoodsItemItineraryType.customizationID, 
	GoodsItemItineraryType.profileID, 
	GoodsItemItineraryType.profileExecutionID, GoodsItemItineraryType.iD, 
	GoodsItemItineraryType.copyIndicator, GoodsItemItineraryType.uUID, 
	GoodsItemItineraryType.issueDate, GoodsItemItineraryType.issueTime, 
	GoodsItemItineraryType.note-list.note, 
	GoodsItemItineraryType.versionID, 
	GoodsItemItineraryType.transportExecutionPlanReferenceID
	AS "urn:oasis:names:specification:ubl:schema:xsd:CommonBasicComponents-2"
	    PREFIX "cbc"
    NAMESPACE GoodsItemItineraryType.signature-list.signature, 
	GoodsItemItineraryType.senderParty, 
	GoodsItemItineraryType.receiverParty, 
	GoodsItemItineraryType.referencedGoodsItem-list.referencedGoodsItem, 
	GoodsItemItineraryType.referencedPackage-list.referencedPackage, 
	GoodsItemItineraryType.referencedTransportEquipment-list.referencedTransportEquipment,
	GoodsItemItineraryType.transportationSegment-list.transportationSegment
	AS "urn:oasis:names:specification:ubl:schema:xsd:CommonAggregateComponents-2"
	    PREFIX "cac"
    NAME GoodsItemItineraryType.uBLExtensions, 
	GoodsItemItineraryType.uBLVersionID, 
	GoodsItemItineraryType.customizationID, 
	GoodsItemItineraryType.profileID, 
	GoodsItemItineraryType.profileExecutionID, GoodsItemItineraryType.iD, 
	GoodsItemItineraryType.copyIndicator, GoodsItemItineraryType.uUID, 
	GoodsItemItineraryType.issueDate, GoodsItemItineraryType.issueTime, 
	GoodsItemItineraryType.note-list.note, 
	GoodsItemItineraryType.versionID, 
	GoodsItemItineraryType.transportExecutionPlanReferenceID, 
	GoodsItemItineraryType.signature-list.signature, 
	GoodsItemItineraryType.senderParty, 
	GoodsItemItineraryType.receiverParty, 
	GoodsItemItineraryType.referencedGoodsItem-list.referencedGoodsItem, 
	GoodsItemItineraryType.referencedPackage-list.referencedPackage, 
	GoodsItemItineraryType.referencedTransportEquipment-list.referencedTransportEquipment,
	GoodsItemItineraryType.transportationSegment-list.transportationSegment
	AS CAPITALIZED
    UNTAGGED SEQUENCE OF
END
