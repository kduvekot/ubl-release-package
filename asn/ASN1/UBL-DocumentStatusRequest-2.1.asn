DocumentStatusRequest-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, TrackingID
    FROM CommonBasicComponents-2
    RequestedDocumentReference, Signature-1, SenderParty, ReceiverParty
    FROM CommonAggregateComponents-2;

DocumentStatusRequest ::= DocumentStatusRequestType

DocumentStatusRequestType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    trackingID TrackingID OPTIONAL,
    requestedDocumentReference RequestedDocumentReference OPTIONAL,
    signature-list SEQUENCE OF signature Signature-1,
    senderParty SenderParty OPTIONAL,
    receiverParty ReceiverParty OPTIONAL
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:DocumentStatusRequest-2"
	PREFIX "ns17"
    NAMESPACE DocumentStatusRequestType.uBLExtensions
	AS "urn:oasis:names:specification:ubl:schema:xsd:CommonExtensionComponents-2"
	    PREFIX "ext"
    NAMESPACE DocumentStatusRequestType.uBLVersionID, 
	DocumentStatusRequestType.customizationID, 
	DocumentStatusRequestType.profileID, 
	DocumentStatusRequestType.profileExecutionID, 
	DocumentStatusRequestType.iD, DocumentStatusRequestType.copyIndicator,
	DocumentStatusRequestType.uUID, DocumentStatusRequestType.issueDate, 
	DocumentStatusRequestType.issueTime, 
	DocumentStatusRequestType.note-list.note, 
	DocumentStatusRequestType.trackingID
	AS "urn:oasis:names:specification:ubl:schema:xsd:CommonBasicComponents-2"
	    PREFIX "cbc"
    NAMESPACE DocumentStatusRequestType.requestedDocumentReference, 
	DocumentStatusRequestType.signature-list.signature, 
	DocumentStatusRequestType.senderParty, 
	DocumentStatusRequestType.receiverParty
	AS "urn:oasis:names:specification:ubl:schema:xsd:CommonAggregateComponents-2"
	    PREFIX "cac"
    NAME DocumentStatusRequestType.uBLExtensions, 
	DocumentStatusRequestType.uBLVersionID, 
	DocumentStatusRequestType.customizationID, 
	DocumentStatusRequestType.profileID, 
	DocumentStatusRequestType.profileExecutionID, 
	DocumentStatusRequestType.iD, DocumentStatusRequestType.copyIndicator,
	DocumentStatusRequestType.uUID, DocumentStatusRequestType.issueDate, 
	DocumentStatusRequestType.issueTime, 
	DocumentStatusRequestType.note-list.note, 
	DocumentStatusRequestType.trackingID, 
	DocumentStatusRequestType.requestedDocumentReference, 
	DocumentStatusRequestType.signature-list.signature, 
	DocumentStatusRequestType.senderParty, 
	DocumentStatusRequestType.receiverParty AS CAPITALIZED
    UNTAGGED SEQUENCE OF
END
