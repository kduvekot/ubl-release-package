XSD {joint-iso-itu-t asn1(1) specification(0) modules(0) xsd-module(2) version2(2)}
DEFINITIONS AUTOMATIC TAGS ::=
BEGIN

XMLCompatibleString ::= UTF8String (FROM (
    {0, 0, 0, 9} | {0, 0, 0, 10} | {0, 0, 0, 13} |
    {0, 0, 0, 32}  .. {0, 0, 215, 255} |
    {0, 0, 224, 0} .. {0, 0, 255, 253} |
    {0, 1, 0, 0}   .. {0, 16, 255, 253}))

XMLStringWithNoWhitespace ::= XMLCompatibleString (FROM (
    {0, 0, 0, 33}  .. {0, 0, 215, 255} | 
    {0, 0, 224, 0} .. {0, 0, 255, 253} | 
    {0, 1, 0, 0}   .. {0, 16, 255, 253}))

XMLStringWithNoCRLFHT ::= UTF8String (FROM (
    {0, 0, 0, 32}  .. {0, 0, 215, 255} | 
    {0, 0, 224, 0} .. {0, 0, 255, 253} | 
    {0, 1, 0, 0}   .. {0, 16, 255, 253}))

/* ASN.1 type definitions supporting the mapping of W3C XML Schema built-in date and time types */
GenericTimeTypeChoice {BasicType, Alternative} ::= CHOICE {
    asn1supportedvalue BasicType,
    othervalues        Alternative}
(CONSTRAINED BY
    {/* The "othervalues" alternative shall not be used for abstract
    values in the "asn1supportedvalue" alternative */})

/* xsd:string */
String ::= XMLCompatibleString

/* xsd:anySympleType */
AnyURI ::= XMLStringWithNoCRLFHT (CONSTRAINED BY {/* The XMLStringWithNoCRLFHT shall be a valid URI as defined in IETF RFC 2396 */})

/* xsd:NCName */
NCName ::= Name (CONSTRAINED BY
    {/* The Name shall be an NCName as defined in W3C XML Namespaces, 2 */})

/* xsd:name */
Name ::= Token (XMLStringWithNoWhitespace) (CONSTRAINED BY
    {/* The Token shall be a Name as defined in W3C XML 1.0, 2.3 */})

/* xsd:token */
Token ::= NormalizedString (CONSTRAINED BY {/* NormalizedString shall be a token as defined in W3C XML Schema Part 2, 3.3.2 */})

/* xsd:normalizedString */
NormalizedString ::= String (XMLStringWithNoCRLFHT) (CONSTRAINED BY {/* String shall be a normalizedString as defined in W3C XML Schema Part 2, 3.3.1 */})

/* xsd:ID */
ID ::= NCName

/* xsd:dateTime */
DateTime ::= TIME (SETTINGS "Basic=Date-Time Date=YMD") (SETTINGS "Midnight=Start")
(CONSTRAINED BY
    {/*The time-zone shall be in the range -14 to +14*/})
(CONSTRAINED BY
    {/*The seconds and fractions of a second shall be less
    than 60 (no leap seconds supported, in accordance with
    W3C XML Schema 1.0 Part 2, 3.2.7)*/})
(CONSTRAINED BY
    {/*The type is constrained to "Time=HMSFn" for any n*/})/* xsd:decimal */

/* xsd:anySympleType */
AnyType ::= SEQUENCE {
    embed-values SEQUENCE OF String,
    attr         SEQUENCE (CONSTRAINED BY
		 {/* Each item shall conform to the "AnyAttributeFormat" 
		     specified in ITU-T Rec. X.693 | ISO/IEC 8825-4,
		     clause 18 */}) OF String,
    elem-list    SEQUENCE OF elem String (CONSTRAINED BY
		 {/* Shall conform to the "AnyElementFormat" specified in
		     ITU-T Rec. X.693 | ISO/IEC 8825-4, clause 19 */})
} (CONSTRAINED BY
    {/* Shall conform to ITU-T Rec. X.693 | ISO/IEC 8825-4, clause 25 */})

/* xsd:language */
Language::= VisibleString (FROM ("a".."z" | "A".."Z" | "-" | "0".."9"))
   (PATTERN "[a-zA-Z]#(1,8)(-[a-zA-Z0-9]#(1,8))*")
   /* The semantics of Language is specified in IETF RFC 3066 */

/* xsd:date */
Date ::= GenericTimeTypeChoice {
    TIME (SETTINGS "Basic=Date Date=YMD"),
    VisibleString(FROM ("0".."9" | "Z:+-"))
(CONSTRAINED BY
    {/* W3C XML Schema 1.0 Part 2, 3.2.9
    and used if a time-zone is present */})}

/* xsd:time */
Time ::= TIME (SETTINGS "Basic=Time") (SETTINGS "Midnight=Start")
(CONSTRAINED BY
    {/*The time-zone shall be in the range -14 to +14*/})
(CONSTRAINED BY
    {/*The seconds and fractions of a second shall be less
    than 60 (no leap seconds supported, in accordance with
    W3C XML Schema 1.0 Part 2, D.2)*/})
(CONSTRAINED BY
    {/*Constrained to "Time=HMSFn" for any n*/})

/* xsd:decimal */
Decimal ::= REAL (WITH COMPONENTS {..., base(10)})
    (ALL EXCEPT(-0 | MINUS-INFINITY | PLUS-INFINITY | NOT-A-NUMBER))

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "http://www.w3.org/2001/XMLSchema"
	PREFIX "xsd"
    NAME String, AnyURI, NormalizedString, Token, DateTime, AnyType, Language,
	Date, Time, Decimal AS UNCAPITALIZED
    NAME ALL IN GenericTimeTypeChoice AS ""
    DECIMAL Decimal
    EMBED-VALUES AnyType
    UNTAGGED AnyType.elem-list
    USE-UNION GenericTimeTypeChoice
    ANY-ATTRIBUTES AnyType.attr
    ANY-ELEMENT AnyType.elem-list.*
    WHITESPACE NormalizedString REPLACE
    WHITESPACE AnyURI, Token, Language COLLAPSE
END
