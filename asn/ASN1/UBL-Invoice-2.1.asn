Invoice-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, DueDate, InvoiceTypeCode, Note,
    TaxPointDate, DocumentCurrencyCode, TaxCurrencyCode, PricingCurrencyCode, 
    PaymentCurrencyCode, PaymentAlternativeCurrencyCode, AccountingCostCode, 
    AccountingCost, LineCountNumeric
    FROM CommonBasicComponents-2
    InvoicePeriod, OrderReference, BillingReference, 
    DespatchDocumentReference, ReceiptDocumentReference, 
    StatementDocumentReference, OriginatorDocumentReference, 
    ContractDocumentReference, AdditionalDocumentReference, Signature-1, 
    AccountingSupplierParty, AccountingCustomerParty, PayeeParty, 
    BuyerCustomerParty, SellerSupplierParty, TaxRepresentativeParty, Delivery,
    DeliveryTerms, PaymentMeans, PaymentTerms, PrepaidPayment, 
    AllowanceCharge, TaxExchangeRate, PricingExchangeRate, 
    PaymentExchangeRate, PaymentAlternativeExchangeRate, TaxTotal, 
    LegalMonetaryTotal, InvoiceLine
    FROM CommonAggregateComponents-2;

Invoice ::= InvoiceType

InvoiceType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    dueDate    DueDate OPTIONAL,
    invoiceTypeCode InvoiceTypeCode OPTIONAL,
    note-list  SEQUENCE OF note Note,
    taxPointDate TaxPointDate OPTIONAL,
    documentCurrencyCode DocumentCurrencyCode OPTIONAL,
    taxCurrencyCode TaxCurrencyCode OPTIONAL,
    pricingCurrencyCode PricingCurrencyCode OPTIONAL,
    paymentCurrencyCode PaymentCurrencyCode OPTIONAL,
    paymentAlternativeCurrencyCode PaymentAlternativeCurrencyCode OPTIONAL,
    accountingCostCode AccountingCostCode OPTIONAL,
    accountingCost AccountingCost OPTIONAL,
    lineCountNumeric LineCountNumeric OPTIONAL,
    invoicePeriod-list SEQUENCE OF invoicePeriod InvoicePeriod,
    orderReference OrderReference OPTIONAL,
    billingReference-list SEQUENCE OF billingReference BillingReference,
    despatchDocumentReference-list SEQUENCE OF despatchDocumentReference 
	DespatchDocumentReference,
    receiptDocumentReference-list SEQUENCE OF receiptDocumentReference 
	ReceiptDocumentReference,
    statementDocumentReference-list SEQUENCE OF statementDocumentReference 
	StatementDocumentReference,
    originatorDocumentReference-list SEQUENCE OF originatorDocumentReference 
	OriginatorDocumentReference,
    contractDocumentReference-list SEQUENCE OF contractDocumentReference 
	ContractDocumentReference,
    additionalDocumentReference-list SEQUENCE OF additionalDocumentReference 
	AdditionalDocumentReference,
    signature-list SEQUENCE OF signature Signature-1,
    accountingSupplierParty AccountingSupplierParty,
    accountingCustomerParty AccountingCustomerParty,
    payeeParty PayeeParty OPTIONAL,
    buyerCustomerParty BuyerCustomerParty OPTIONAL,
    sellerSupplierParty SellerSupplierParty OPTIONAL,
    taxRepresentativeParty TaxRepresentativeParty OPTIONAL,
    delivery-list SEQUENCE OF delivery Delivery,
    deliveryTerms DeliveryTerms OPTIONAL,
    paymentMeans-list SEQUENCE OF paymentMeans PaymentMeans,
    paymentTerms-list SEQUENCE OF paymentTerms PaymentTerms,
    prepaidPayment-list SEQUENCE OF prepaidPayment PrepaidPayment,
    allowanceCharge-list SEQUENCE OF allowanceCharge AllowanceCharge,
    taxExchangeRate TaxExchangeRate OPTIONAL,
    pricingExchangeRate PricingExchangeRate OPTIONAL,
    paymentExchangeRate PaymentExchangeRate OPTIONAL,
    paymentAlternativeExchangeRate PaymentAlternativeExchangeRate OPTIONAL,
    taxTotal-list SEQUENCE OF taxTotal TaxTotal,
    legalMonetaryTotal LegalMonetaryTotal,
    invoiceLine-list SEQUENCE (SIZE(1..MAX)) OF invoiceLine InvoiceLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:Invoice-2"
	PREFIX "ns28"
    NAMESPACE InvoiceType.uBLExtensions
	AS "urn:oasis:names:specification:ubl:schema:xsd:CommonExtensionComponents-2"
	    PREFIX "ext"
    NAMESPACE InvoiceType.uBLVersionID, InvoiceType.customizationID, 
	InvoiceType.profileID, InvoiceType.profileExecutionID, InvoiceType.iD,
	InvoiceType.copyIndicator, InvoiceType.uUID, InvoiceType.issueDate, 
	InvoiceType.issueTime, InvoiceType.dueDate, 
	InvoiceType.invoiceTypeCode, InvoiceType.note-list.note, 
	InvoiceType.taxPointDate, InvoiceType.documentCurrencyCode, 
	InvoiceType.taxCurrencyCode, InvoiceType.pricingCurrencyCode, 
	InvoiceType.paymentCurrencyCode, 
	InvoiceType.paymentAlternativeCurrencyCode, 
	InvoiceType.accountingCostCode, InvoiceType.accountingCost, 
	InvoiceType.lineCountNumeric
	AS "urn:oasis:names:specification:ubl:schema:xsd:CommonBasicComponents-2"
	    PREFIX "cbc"
    NAMESPACE InvoiceType.invoicePeriod-list.invoicePeriod, 
	InvoiceType.orderReference, 
	InvoiceType.billingReference-list.billingReference, 
	InvoiceType.despatchDocumentReference-list.despatchDocumentReference, 
	InvoiceType.receiptDocumentReference-list.receiptDocumentReference, 
	InvoiceType.statementDocumentReference-list.statementDocumentReference,
	InvoiceType.originatorDocumentReference-list.originatorDocumentReference,
	InvoiceType.contractDocumentReference-list.contractDocumentReference, 
	InvoiceType.additionalDocumentReference-list.additionalDocumentReference,
	InvoiceType.signature-list.signature, 
	InvoiceType.accountingSupplierParty, 
	InvoiceType.accountingCustomerParty, InvoiceType.payeeParty, 
	InvoiceType.buyerCustomerParty, InvoiceType.sellerSupplierParty, 
	InvoiceType.taxRepresentativeParty, 
	InvoiceType.delivery-list.delivery, InvoiceType.deliveryTerms, 
	InvoiceType.paymentMeans-list.paymentMeans, 
	InvoiceType.paymentTerms-list.paymentTerms, 
	InvoiceType.prepaidPayment-list.prepaidPayment, 
	InvoiceType.allowanceCharge-list.allowanceCharge, 
	InvoiceType.taxExchangeRate, InvoiceType.pricingExchangeRate, 
	InvoiceType.paymentExchangeRate, 
	InvoiceType.paymentAlternativeExchangeRate, 
	InvoiceType.taxTotal-list.taxTotal, InvoiceType.legalMonetaryTotal, 
	InvoiceType.invoiceLine-list.invoiceLine
	AS "urn:oasis:names:specification:ubl:schema:xsd:CommonAggregateComponents-2"
	    PREFIX "cac"
    NAME InvoiceType.uBLExtensions, InvoiceType.uBLVersionID, 
	InvoiceType.customizationID, InvoiceType.profileID, 
	InvoiceType.profileExecutionID, InvoiceType.iD, 
	InvoiceType.copyIndicator, InvoiceType.uUID, InvoiceType.issueDate, 
	InvoiceType.issueTime, InvoiceType.dueDate, 
	InvoiceType.invoiceTypeCode, InvoiceType.note-list.note, 
	InvoiceType.taxPointDate, InvoiceType.documentCurrencyCode, 
	InvoiceType.taxCurrencyCode, InvoiceType.pricingCurrencyCode, 
	InvoiceType.paymentCurrencyCode, 
	InvoiceType.paymentAlternativeCurrencyCode, 
	InvoiceType.accountingCostCode, InvoiceType.accountingCost, 
	InvoiceType.lineCountNumeric, 
	InvoiceType.invoicePeriod-list.invoicePeriod, 
	InvoiceType.orderReference, 
	InvoiceType.billingReference-list.billingReference, 
	InvoiceType.despatchDocumentReference-list.despatchDocumentReference, 
	InvoiceType.receiptDocumentReference-list.receiptDocumentReference, 
	InvoiceType.statementDocumentReference-list.statementDocumentReference,
	InvoiceType.originatorDocumentReference-list.originatorDocumentReference,
	InvoiceType.contractDocumentReference-list.contractDocumentReference, 
	InvoiceType.additionalDocumentReference-list.additionalDocumentReference,
	InvoiceType.signature-list.signature, 
	InvoiceType.accountingSupplierParty, 
	InvoiceType.accountingCustomerParty, InvoiceType.payeeParty, 
	InvoiceType.buyerCustomerParty, InvoiceType.sellerSupplierParty, 
	InvoiceType.taxRepresentativeParty, 
	InvoiceType.delivery-list.delivery, InvoiceType.deliveryTerms, 
	InvoiceType.paymentMeans-list.paymentMeans, 
	InvoiceType.paymentTerms-list.paymentTerms, 
	InvoiceType.prepaidPayment-list.prepaidPayment, 
	InvoiceType.allowanceCharge-list.allowanceCharge, 
	InvoiceType.taxExchangeRate, InvoiceType.pricingExchangeRate, 
	InvoiceType.paymentExchangeRate, 
	InvoiceType.paymentAlternativeExchangeRate, 
	InvoiceType.taxTotal-list.taxTotal, InvoiceType.legalMonetaryTotal, 
	InvoiceType.invoiceLine-list.invoiceLine AS CAPITALIZED
    UNTAGGED SEQUENCE OF
END
