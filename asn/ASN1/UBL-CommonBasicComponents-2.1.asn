CommonBasicComponents-2
DEFINITIONS AUTOMATIC TAGS ::=
BEGIN
IMPORTS 
    Language, NormalizedString, String, AnyURI, Date, Time, Decimal
    FROM XSD;

AcceptedIndicator ::= AcceptedIndicatorType

AcceptedVariantsDescription ::= AcceptedVariantsDescriptionType

AccountFormatCode ::= AccountFormatCodeType

AccountID ::= AccountIDType

AccountTypeCode ::= AccountTypeCodeType

AccountingCost ::= AccountingCostType

AccountingCostCode ::= AccountingCostCodeType

ActionCode ::= ActionCodeType

ActivityCode ::= ActivityCodeType

ActualDeliveryDate ::= ActualDeliveryDateType

ActualDeliveryTime ::= ActualDeliveryTimeType

ActualDespatchDate ::= ActualDespatchDateType

ActualDespatchTime ::= ActualDespatchTimeType

ActualPickupDate ::= ActualPickupDateType

ActualPickupTime ::= ActualPickupTimeType

ActualTemperatureReductionQuantity ::= ActualTemperatureReductionQuantityType

AdValoremIndicator ::= AdValoremIndicatorType

AdditionalAccountID ::= AdditionalAccountIDType

AdditionalInformation ::= AdditionalInformationType

AdditionalStreetName ::= AdditionalStreetNameType

AddressFormatCode ::= AddressFormatCodeType

AddressTypeCode ::= AddressTypeCodeType

AdjustmentReasonCode ::= AdjustmentReasonCodeType

AdmissionCode ::= AdmissionCodeType

AdvertisementAmount ::= AdvertisementAmountType

AgencyID ::= AgencyIDType

AgencyName ::= AgencyNameType

AirFlowPercent ::= AirFlowPercentType

AircraftID ::= AircraftIDType

AliasName ::= AliasNameType

AllowanceChargeReason ::= AllowanceChargeReasonType

AllowanceChargeReasonCode ::= AllowanceChargeReasonCodeType

AllowanceTotalAmount ::= AllowanceTotalAmountType

AltitudeMeasure ::= AltitudeMeasureType

Amount ::= AmountType

AmountRate ::= AmountRateType

AnimalFoodApprovedIndicator ::= AnimalFoodApprovedIndicatorType

AnimalFoodIndicator ::= AnimalFoodIndicatorType

AnnualAverageAmount ::= AnnualAverageAmountType

ApplicationStatusCode ::= ApplicationStatusCodeType

ApprovalDate ::= ApprovalDateType

ApprovalStatus ::= ApprovalStatusType

AttributeID ::= AttributeIDType

AuctionConstraintIndicator ::= AuctionConstraintIndicatorType

AuctionURI ::= AuctionURIType

AvailabilityDate ::= AvailabilityDateType

AvailabilityStatusCode ::= AvailabilityStatusCodeType

AverageAmount ::= AverageAmountType

AverageSubsequentContractAmount ::= AverageSubsequentContractAmountType

AwardDate ::= AwardDateType

AwardTime ::= AwardTimeType

AwardingCriteriaDescription ::= AwardingCriteriaDescriptionType

AwardingCriteriaID ::= AwardingCriteriaIDType

AwardingCriteriaTypeCode ::= AwardingCriteriaTypeCodeType

AwardingMethodTypeCode ::= AwardingMethodTypeCodeType

BackOrderAllowedIndicator ::= BackOrderAllowedIndicatorType

BackorderQuantity ::= BackorderQuantityType

BackorderReason ::= BackorderReasonType

BalanceAmount ::= BalanceAmountType

BalanceBroughtForwardIndicator ::= BalanceBroughtForwardIndicatorType

BaseAmount ::= BaseAmountType

BaseQuantity ::= BaseQuantityType

BaseUnitMeasure ::= BaseUnitMeasureType

BasedOnConsensusIndicator ::= BasedOnConsensusIndicatorType

BasicConsumedQuantity ::= BasicConsumedQuantityType

BatchQuantity ::= BatchQuantityType

BestBeforeDate ::= BestBeforeDateType

BirthDate ::= BirthDateType

BlockName ::= BlockNameType

BrandName ::= BrandNameType

BrokerAssignedID ::= BrokerAssignedIDType

BudgetYearNumeric ::= BudgetYearNumericType

BuildingName ::= BuildingNameType

BuildingNumber ::= BuildingNumberType

BulkCargoIndicator ::= BulkCargoIndicatorType

BusinessClassificationEvidenceID ::= BusinessClassificationEvidenceIDType

BusinessIdentityEvidenceID ::= BusinessIdentityEvidenceIDType

BuyerEventID ::= BuyerEventIDType

BuyerProfileURI ::= BuyerProfileURIType

CV2ID ::= CV2IDType

CalculationExpression ::= CalculationExpressionType

CalculationExpressionCode ::= CalculationExpressionCodeType

CalculationRate ::= CalculationRateType

CalculationSequenceNumeric ::= CalculationSequenceNumericType

CallBaseAmount ::= CallBaseAmountType

CallDate ::= CallDateType

CallExtensionAmount ::= CallExtensionAmountType

CallTime ::= CallTimeType

CancellationNote ::= CancellationNoteType

CandidateReductionConstraintIndicator ::= 
    CandidateReductionConstraintIndicatorType

CanonicalizationMethod-1 ::= CanonicalizationMethodType-1

CapabilityTypeCode ::= CapabilityTypeCodeType

CardChipCode ::= CardChipCodeType

CardTypeCode ::= CardTypeCodeType

CargoTypeCode ::= CargoTypeCodeType

CarrierAssignedID ::= CarrierAssignedIDType

CarrierServiceInstructions ::= CarrierServiceInstructionsType

CatalogueIndicator ::= CatalogueIndicatorType

CategoryName ::= CategoryNameType

CertificateType-1 ::= CertificateTypeType

CertificateTypeCode ::= CertificateTypeCodeType

ChangeConditions ::= ChangeConditionsType

Channel ::= ChannelType

ChannelCode ::= ChannelCodeType

CharacterSetCode ::= CharacterSetCodeType

Characteristics ::= CharacteristicsType

ChargeIndicator ::= ChargeIndicatorType

ChargeTotalAmount ::= ChargeTotalAmountType

ChargeableQuantity ::= ChargeableQuantityType

ChargeableWeightMeasure ::= ChargeableWeightMeasureType

ChipApplicationID ::= ChipApplicationIDType

CityName ::= CityNameType

CitySubdivisionName ::= CitySubdivisionNameType

Clause ::= ClauseType

ClauseCode ::= ClauseCodeType

CodeValue ::= CodeValueType

CollaborationPriorityCode ::= CollaborationPriorityCodeType

Comment ::= CommentType

CommodityCode ::= CommodityCodeType

CompanyID ::= CompanyIDType

CompanyLegalFormCode ::= CompanyLegalFormCodeType

CompanyLiquidationStatusCode ::= CompanyLiquidationStatusCodeType

ComparedValueMeasure ::= ComparedValueMeasureType

ComparisonDataCode ::= ComparisonDataCodeType

ComparisonDataSourceCode ::= ComparisonDataSourceCodeType

ComparisonForecastIssueDate ::= ComparisonForecastIssueDateType

ComparisonForecastIssueTime ::= ComparisonForecastIssueTimeType

CompletionIndicator ::= CompletionIndicatorType

Condition ::= ConditionType

ConditionCode ::= ConditionCodeType

ConditionDeviationIndicator ::= ConditionDeviationIndicatorType

ConditionValueMeasure ::= ConditionValueMeasureType

Conditions ::= ConditionsType

ConditionsDescription ::= ConditionsDescriptionType

ConsigneeAssignedID ::= ConsigneeAssignedIDType

ConsignmentQuantity ::= ConsignmentQuantityType

ConsignorAssignedID ::= ConsignorAssignedIDType

ConsolidatableIndicator ::= ConsolidatableIndicatorType

ConstitutionCode ::= ConstitutionCodeType

ConsumerIncentiveTacticTypeCode ::= ConsumerIncentiveTacticTypeCodeType

ConsumerUnitQuantity ::= ConsumerUnitQuantityType

ConsumersEnergyLevel ::= ConsumersEnergyLevelType

ConsumersEnergyLevelCode ::= ConsumersEnergyLevelCodeType

ConsumptionEnergyQuantity ::= ConsumptionEnergyQuantityType

ConsumptionID ::= ConsumptionIDType

ConsumptionLevel ::= ConsumptionLevelType

ConsumptionLevelCode ::= ConsumptionLevelCodeType

ConsumptionReportID ::= ConsumptionReportIDType

ConsumptionType-1 ::= ConsumptionTypeType

ConsumptionTypeCode ::= ConsumptionTypeCodeType

ConsumptionWaterQuantity ::= ConsumptionWaterQuantityType

ContainerizedIndicator ::= ContainerizedIndicatorType

ContentUnitQuantity ::= ContentUnitQuantityType

ContractFolderID ::= ContractFolderIDType

ContractName ::= ContractNameType

ContractSubdivision ::= ContractSubdivisionType

ContractType-1 ::= ContractTypeType

ContractTypeCode ::= ContractTypeCodeType

ContractedCarrierAssignedID ::= ContractedCarrierAssignedIDType

ContractingPartyTypeCode ::= ContractingPartyTypeCodeType

ContractingSystemCode ::= ContractingSystemCodeType

CoordinateSystemCode ::= CoordinateSystemCodeType

CopyIndicator ::= CopyIndicatorType

CorporateRegistrationTypeCode ::= CorporateRegistrationTypeCodeType

CorporateStockAmount ::= CorporateStockAmountType

CorrectionAmount ::= CorrectionAmountType

CorrectionType-1 ::= CorrectionTypeType

CorrectionTypeCode ::= CorrectionTypeCodeType

CorrectionUnitAmount ::= CorrectionUnitAmountType

CountrySubentity ::= CountrySubentityType

CountrySubentityCode ::= CountrySubentityCodeType

CreditLineAmount ::= CreditLineAmountType

CreditedQuantity ::= CreditedQuantityType

CurrencyCode ::= CurrencyCodeType

CurrentChargeType ::= CurrentChargeTypeType

CurrentChargeTypeCode ::= CurrentChargeTypeCodeType

CustomerAssignedAccountID ::= CustomerAssignedAccountIDType

CustomerReference ::= CustomerReferenceType

CustomizationID ::= CustomizationIDType

CustomsClearanceServiceInstructions ::= 
    CustomsClearanceServiceInstructionsType

CustomsImportClassifiedIndicator ::= CustomsImportClassifiedIndicatorType

CustomsStatusCode ::= CustomsStatusCodeType

CustomsTariffQuantity ::= CustomsTariffQuantityType

DamageRemarks ::= DamageRemarksType

DangerousGoodsApprovedIndicator ::= DangerousGoodsApprovedIndicatorType

DataSendingCapability ::= DataSendingCapabilityType

DataSourceCode ::= DataSourceCodeType

Date-1 ::= DateType

DebitLineAmount ::= DebitLineAmountType

DebitedQuantity ::= DebitedQuantityType

DeclarationTypeCode ::= DeclarationTypeCodeType

DeclaredCarriageValueAmount ::= DeclaredCarriageValueAmountType

DeclaredCustomsValueAmount ::= DeclaredCustomsValueAmountType

DeclaredForCarriageValueAmount ::= DeclaredForCarriageValueAmountType

DeclaredStatisticsValueAmount ::= DeclaredStatisticsValueAmountType

DeliveredQuantity ::= DeliveredQuantityType

DeliveryInstructions ::= DeliveryInstructionsType

DemurrageInstructions ::= DemurrageInstructionsType

Department ::= DepartmentType

Description ::= DescriptionType

DescriptionCode ::= DescriptionCodeType

DespatchAdviceTypeCode ::= DespatchAdviceTypeCodeType

DifferenceTemperatureReductionQuantity ::= 
    DifferenceTemperatureReductionQuantityType

DirectionCode ::= DirectionCodeType

DisplayTacticTypeCode ::= DisplayTacticTypeCodeType

DispositionCode ::= DispositionCodeType

District ::= DistrictType

DocumentCurrencyCode ::= DocumentCurrencyCodeType

DocumentDescription ::= DocumentDescriptionType

DocumentHash ::= DocumentHashType

DocumentID ::= DocumentIDType

DocumentStatusCode ::= DocumentStatusCodeType

DocumentType ::= DocumentTypeType

DocumentTypeCode ::= DocumentTypeCodeType

DueDate ::= DueDateType

DurationMeasure ::= DurationMeasureType

Duty-1 ::= DutyType-1

DutyCode ::= DutyCodeType

EarliestPickupDate ::= EarliestPickupDateType

EarliestPickupTime ::= EarliestPickupTimeType

EconomicOperatorRegistryURI ::= EconomicOperatorRegistryURIType

EffectiveDate ::= EffectiveDateType

EffectiveTime ::= EffectiveTimeType

ElectronicDeviceDescription ::= ElectronicDeviceDescriptionType

ElectronicMail ::= ElectronicMailType

EmbeddedDocumentBinaryObject ::= EmbeddedDocumentBinaryObjectType

EmergencyProceduresCode ::= EmergencyProceduresCodeType

EmployeeQuantity ::= EmployeeQuantityType

EncodingCode ::= EncodingCodeType

EndDate ::= EndDateType

EndTime ::= EndTimeType

EndpointID ::= EndpointIDType

EnvironmentalEmissionTypeCode ::= EnvironmentalEmissionTypeCodeType

EstimatedConsumedQuantity ::= EstimatedConsumedQuantityType

EstimatedDeliveryDate ::= EstimatedDeliveryDateType

EstimatedDeliveryTime ::= EstimatedDeliveryTimeType

EstimatedDespatchDate ::= EstimatedDespatchDateType

EstimatedDespatchTime ::= EstimatedDespatchTimeType

EstimatedOverallContractAmount ::= EstimatedOverallContractAmountType

EstimatedOverallContractQuantity ::= EstimatedOverallContractQuantityType

EvaluationCriteriaTypeCode ::= EvaluationCriteriaTypeCodeType

EvidenceSuppliedID ::= EvidenceSuppliedIDType

EvidenceTypeCode ::= EvidenceTypeCodeType

ExceptionResolutionCode ::= ExceptionResolutionCodeType

ExceptionStatusCode ::= ExceptionStatusCodeType

ExchangeMarketID ::= ExchangeMarketIDType

ExclusionReason ::= ExclusionReasonType

ExecutionRequirementCode ::= ExecutionRequirementCodeType

ExemptionReason ::= ExemptionReasonType

ExemptionReasonCode ::= ExemptionReasonCodeType

ExpectedOperatorQuantity ::= ExpectedOperatorQuantityType

ExpectedQuantity ::= ExpectedQuantityType

ExpenseCode ::= ExpenseCodeType

ExpiryDate ::= ExpiryDateType

ExpiryTime ::= ExpiryTimeType

ExpressionCode ::= ExpressionCodeType

ExtendedID ::= ExtendedIDType

Extension ::= ExtensionType

FaceValueAmount ::= FaceValueAmountType

FamilyName ::= FamilyNameType

FeatureTacticTypeCode ::= FeatureTacticTypeCodeType

FeeAmount ::= FeeAmountType

FeeDescription ::= FeeDescriptionType

FileName ::= FileNameType

FinancingInstrumentCode ::= FinancingInstrumentCodeType

FirstName ::= FirstNameType

FirstShipmentAvailibilityDate ::= FirstShipmentAvailibilityDateType

Floor ::= FloorType

ForecastPurposeCode ::= ForecastPurposeCodeType

ForecastTypeCode ::= ForecastTypeCodeType

FormatCode ::= FormatCodeType

ForwarderServiceInstructions ::= ForwarderServiceInstructionsType

FreeOfChargeIndicator ::= FreeOfChargeIndicatorType

FreeOnBoardValueAmount ::= FreeOnBoardValueAmountType

FreightForwarderAssignedID ::= FreightForwarderAssignedIDType

FreightRateClassCode ::= FreightRateClassCodeType

Frequency ::= FrequencyType

FrozenDocumentIndicator ::= FrozenDocumentIndicatorType

FrozenPeriodDaysNumeric ::= FrozenPeriodDaysNumericType

FullnessIndicationCode ::= FullnessIndicationCodeType

FullyPaidSharesIndicator ::= FullyPaidSharesIndicatorType

FundingProgram ::= FundingProgramType

FundingProgramCode ::= FundingProgramCodeType

GasPressureQuantity ::= GasPressureQuantityType

GenderCode ::= GenderCodeType

GeneralCargoIndicator ::= GeneralCargoIndicatorType

GovernmentAgreementConstraintIndicator ::= 
    GovernmentAgreementConstraintIndicatorType

GrossVolumeMeasure ::= GrossVolumeMeasureType

GrossWeightMeasure ::= GrossWeightMeasureType

GuaranteeTypeCode ::= GuaranteeTypeCodeType

GuaranteedDespatchDate ::= GuaranteedDespatchDateType

GuaranteedDespatchTime ::= GuaranteedDespatchTimeType

HandlingCode ::= HandlingCodeType

HandlingInstructions ::= HandlingInstructionsType

HashAlgorithmMethod ::= HashAlgorithmMethodType

HaulageInstructions ::= HaulageInstructionsType

HazardClassID ::= HazardClassIDType

HazardousCategoryCode ::= HazardousCategoryCodeType

HazardousRegulationCode ::= HazardousRegulationCodeType

HazardousRiskIndicator ::= HazardousRiskIndicatorType

HeatingType ::= HeatingTypeType

HeatingTypeCode ::= HeatingTypeCodeType

HigherTenderAmount ::= HigherTenderAmountType

HolderName ::= HolderNameType

HumanFoodApprovedIndicator ::= HumanFoodApprovedIndicatorType

HumanFoodIndicator ::= HumanFoodIndicatorType

HumidityPercent ::= HumidityPercentType

ID-1 ::= IDType

IdentificationCode ::= IdentificationCodeType

IdentificationID ::= IdentificationIDType

ImmobilizationCertificateID ::= ImmobilizationCertificateIDType

ImportanceCode ::= ImportanceCodeType

IndicationIndicator ::= IndicationIndicatorType

IndustryClassificationCode ::= IndustryClassificationCodeType

Information ::= InformationType

InformationURI ::= InformationURIType

InhalationToxicityZoneCode ::= InhalationToxicityZoneCodeType

InhouseMail ::= InhouseMailType

InspectionMethodCode ::= InspectionMethodCodeType

InstallmentDueDate ::= InstallmentDueDateType

InstructionID ::= InstructionIDType

InstructionNote ::= InstructionNoteType

Instructions ::= InstructionsType

InsurancePremiumAmount ::= InsurancePremiumAmountType

InsuranceValueAmount ::= InsuranceValueAmountType

InterestedProcurementLotsID ::= InterestedProcurementLotsIDType

InventoryValueAmount ::= InventoryValueAmountType

InvoiceTypeCode ::= InvoiceTypeCodeType

InvoicedQuantity ::= InvoicedQuantityType

InvoicingPartyReference ::= InvoicingPartyReferenceType

IssueDate ::= IssueDateType

IssueNumberID ::= IssueNumberIDType

IssueTime ::= IssueTimeType

IssuerID ::= IssuerIDType

ItemClassificationCode ::= ItemClassificationCodeType

ItemUpdateRequestIndicator ::= ItemUpdateRequestIndicatorType

JobTitle ::= JobTitleType

JourneyID ::= JourneyIDType

Justification ::= JustificationType

JustificationDescription ::= JustificationDescriptionType

Keyword ::= KeywordType

LanguageID ::= LanguageIDType

LastRevisionDate ::= LastRevisionDateType

LastRevisionTime ::= LastRevisionTimeType

LatestDeliveryDate ::= LatestDeliveryDateType

LatestDeliveryTime ::= LatestDeliveryTimeType

LatestMeterQuantity ::= LatestMeterQuantityType

LatestMeterReadingDate ::= LatestMeterReadingDateType

LatestPickupDate ::= LatestPickupDateType

LatestPickupTime ::= LatestPickupTimeType

LatestProposalAcceptanceDate ::= LatestProposalAcceptanceDateType

LatitudeDegreesMeasure ::= LatitudeDegreesMeasureType

LatitudeDirectionCode ::= LatitudeDirectionCodeType

LatitudeMinutesMeasure ::= LatitudeMinutesMeasureType

LeadTimeMeasure ::= LeadTimeMeasureType

LegalForm ::= LegalFormType

LegalReference ::= LegalReferenceType

LegalStatusIndicator ::= LegalStatusIndicatorType

LiabilityAmount ::= LiabilityAmountType

LicensePlateID ::= LicensePlateIDType

LifeCycleStatusCode ::= LifeCycleStatusCodeType

LimitationDescription ::= LimitationDescriptionType

Line ::= LineType

LineCountNumeric ::= LineCountNumericType

LineExtensionAmount ::= LineExtensionAmountType

LineID ::= LineIDType

LineNumberNumeric ::= LineNumberNumericType

LineStatusCode ::= LineStatusCodeType

ListValue ::= ListValueType

LivestockIndicator ::= LivestockIndicatorType

LoadingLengthMeasure ::= LoadingLengthMeasureType

LoadingSequenceID ::= LoadingSequenceIDType

LocaleCode ::= LocaleCodeType

Location-1 ::= LocationType-1

LocationID ::= LocationIDType

LocationTypeCode ::= LocationTypeCodeType

Login ::= LoginType

LogoReferenceID ::= LogoReferenceIDType

LongitudeDegreesMeasure ::= LongitudeDegreesMeasureType

LongitudeDirectionCode ::= LongitudeDirectionCodeType

LongitudeMinutesMeasure ::= LongitudeMinutesMeasureType

LossRisk ::= LossRiskType

LossRiskResponsibilityCode ::= LossRiskResponsibilityCodeType

LotNumberID ::= LotNumberIDType

LowTendersDescription ::= LowTendersDescriptionType

LowerOrangeHazardPlacardID ::= LowerOrangeHazardPlacardIDType

LowerTenderAmount ::= LowerTenderAmountType

MandateTypeCode ::= MandateTypeCodeType

ManufactureDate ::= ManufactureDateType

ManufactureTime ::= ManufactureTimeType

MarkAttention ::= MarkAttentionType

MarkAttentionIndicator ::= MarkAttentionIndicatorType

MarkCare ::= MarkCareType

MarkCareIndicator ::= MarkCareIndicatorType

MarketValueAmount ::= MarketValueAmountType

MarkingID ::= MarkingIDType

MathematicOperatorCode ::= MathematicOperatorCodeType

MaximumAdvertisementAmount ::= MaximumAdvertisementAmountType

MaximumAmount ::= MaximumAmountType

MaximumBackorderQuantity ::= MaximumBackorderQuantityType

MaximumCopiesNumeric ::= MaximumCopiesNumericType

MaximumMeasure ::= MaximumMeasureType

MaximumNumberNumeric ::= MaximumNumberNumericType

MaximumOperatorQuantity ::= MaximumOperatorQuantityType

MaximumOrderQuantity ::= MaximumOrderQuantityType

MaximumPaidAmount ::= MaximumPaidAmountType

MaximumPaymentInstructionsNumeric ::= MaximumPaymentInstructionsNumericType

MaximumQuantity ::= MaximumQuantityType

MaximumTaxExclusiveAmount ::= MaximumTaxExclusiveAmountType

MaximumTaxInclusiveAmount ::= MaximumTaxInclusiveAmountType

MaximumValue ::= MaximumValueType

MaximumVariantQuantity ::= MaximumVariantQuantityType

Measure ::= MeasureType

MedicalFirstAidGuideCode ::= MedicalFirstAidGuideCodeType

MeterConstant ::= MeterConstantType

MeterConstantCode ::= MeterConstantCodeType

MeterName ::= MeterNameType

MeterNumber ::= MeterNumberType

MeterReadingComments ::= MeterReadingCommentsType

MeterReadingMethod ::= MeterReadingMethodType

MeterReadingMethodCode ::= MeterReadingMethodCodeType

MeterReadingType-1 ::= MeterReadingTypeType

MeterReadingTypeCode ::= MeterReadingTypeCodeType

MiddleName ::= MiddleNameType

MimeCode ::= MimeCodeType

MinimumAmount ::= MinimumAmountType

MinimumBackorderQuantity ::= MinimumBackorderQuantityType

MinimumImprovementBid ::= MinimumImprovementBidType

MinimumInventoryQuantity ::= MinimumInventoryQuantityType

MinimumMeasure ::= MinimumMeasureType

MinimumNumberNumeric ::= MinimumNumberNumericType

MinimumOrderQuantity ::= MinimumOrderQuantityType

MinimumQuantity ::= MinimumQuantityType

MinimumValue ::= MinimumValueType

MiscellaneousEventTypeCode ::= MiscellaneousEventTypeCodeType

ModelName ::= ModelNameType

MonetaryScope ::= MonetaryScopeType

MovieTitle ::= MovieTitleType

MultipleOrderQuantity ::= MultipleOrderQuantityType

MultiplierFactorNumeric ::= MultiplierFactorNumericType

Name-1 ::= NameType

NameCode ::= NameCodeType

NameSuffix ::= NameSuffixType

NationalityID ::= NationalityIDType

NatureCode ::= NatureCodeType

NegotiationDescription ::= NegotiationDescriptionType

NetNetWeightMeasure ::= NetNetWeightMeasureType

NetVolumeMeasure ::= NetVolumeMeasureType

NetWeightMeasure ::= NetWeightMeasureType

NetworkID ::= NetworkIDType

NominationDate ::= NominationDateType

NominationTime ::= NominationTimeType

NormalTemperatureReductionQuantity ::= NormalTemperatureReductionQuantityType

Note ::= NoteType

NotificationTypeCode ::= NotificationTypeCodeType

OccurrenceDate ::= OccurrenceDateType

OccurrenceTime ::= OccurrenceTimeType

OnCarriageIndicator ::= OnCarriageIndicatorType

OneTimeChargeType ::= OneTimeChargeTypeType

OneTimeChargeTypeCode ::= OneTimeChargeTypeCodeType

OntologyURI ::= OntologyURIType

OpenTenderID ::= OpenTenderIDType

OperatingYearsQuantity ::= OperatingYearsQuantityType

OperationStatusCode ::= OperationStatusCodeType

OptionalLineItemIndicator ::= OptionalLineItemIndicatorType

OptionsDescription ::= OptionsDescriptionType

OrderIntervalDaysNumeric ::= OrderIntervalDaysNumericType

OrderQuantityIncrementNumeric ::= OrderQuantityIncrementNumericType

OrderResponseCode ::= OrderResponseCodeType

OrderTypeCode ::= OrderTypeCodeType

OrderableIndicator ::= OrderableIndicatorType

OrderableUnit ::= OrderableUnitType

OrderableUnitFactorRate ::= OrderableUnitFactorRateType

OrganizationDepartment ::= OrganizationDepartmentType

OriginalContractingSystemID ::= OriginalContractingSystemIDType

OriginalJobID ::= OriginalJobIDType

OtherInstruction ::= OtherInstructionType

OutstandingQuantity ::= OutstandingQuantityType

OutstandingReason ::= OutstandingReasonType

OversupplyQuantity ::= OversupplyQuantityType

OwnerTypeCode ::= OwnerTypeCodeType

PackLevelCode ::= PackLevelCodeType

PackQuantity ::= PackQuantityType

PackSizeNumeric ::= PackSizeNumericType

PackageLevelCode ::= PackageLevelCodeType

PackagingTypeCode ::= PackagingTypeCodeType

PackingCriteriaCode ::= PackingCriteriaCodeType

PackingMaterial ::= PackingMaterialType

PaidAmount ::= PaidAmountType

PaidDate ::= PaidDateType

PaidTime ::= PaidTimeType

ParentDocumentID ::= ParentDocumentIDType

ParentDocumentLineReferenceID ::= ParentDocumentLineReferenceIDType

ParentDocumentTypeCode ::= ParentDocumentTypeCodeType

ParentDocumentVersionID ::= ParentDocumentVersionIDType

PartPresentationCode ::= PartPresentationCodeType

PartecipationPercent ::= PartecipationPercentType

PartialDeliveryIndicator ::= PartialDeliveryIndicatorType

ParticipationPercent ::= ParticipationPercentType

PartyCapacityAmount ::= PartyCapacityAmountType

Password ::= PasswordType

PayPerView ::= PayPerViewType

PayableAlternativeAmount ::= PayableAlternativeAmountType

PayableAmount ::= PayableAmountType

PayableRoundingAmount ::= PayableRoundingAmountType

PayerReference ::= PayerReferenceType

PaymentAlternativeCurrencyCode ::= PaymentAlternativeCurrencyCodeType

PaymentChannelCode ::= PaymentChannelCodeType

PaymentCurrencyCode ::= PaymentCurrencyCodeType

PaymentDueDate ::= PaymentDueDateType

PaymentFrequencyCode ::= PaymentFrequencyCodeType

PaymentID ::= PaymentIDType

PaymentMeansCode ::= PaymentMeansCodeType

PaymentMeansID ::= PaymentMeansIDType

PaymentNote ::= PaymentNoteType

PaymentOrderReference ::= PaymentOrderReferenceType

PaymentPercent ::= PaymentPercentType

PaymentPurposeCode ::= PaymentPurposeCodeType

PaymentTermsDetailsURI ::= PaymentTermsDetailsURIType

PenaltyAmount ::= PenaltyAmountType

PenaltyClauses ::= PenaltyClausesType

PenaltySurchargePercent ::= PenaltySurchargePercentType

PerUnitAmount ::= PerUnitAmountType

Percent ::= PercentType

PerformanceMetricTypeCode ::= PerformanceMetricTypeCodeType

PerformanceValueQuantity ::= PerformanceValueQuantityType

PerformingCarrierAssignedID ::= PerformingCarrierAssignedIDType

PersonalSituation ::= PersonalSituationType

PhoneNumber ::= PhoneNumberType

PlacardEndorsement ::= PlacardEndorsementType

PlacardNotation ::= PlacardNotationType

PlannedDate ::= PlannedDateType

PlotIdentification ::= PlotIdentificationType

PositionCode ::= PositionCodeType

PostalZone ::= PostalZoneType

Postbox ::= PostboxType

PowerIndicator ::= PowerIndicatorType

PreCarriageIndicator ::= PreCarriageIndicatorType

PreferenceCriterionCode ::= PreferenceCriterionCodeType

PrepaidAmount ::= PrepaidAmountType

PrepaidIndicator ::= PrepaidIndicatorType

PrepaidPaymentReferenceID ::= PrepaidPaymentReferenceIDType

PreviousCancellationReasonCode ::= PreviousCancellationReasonCodeType

PreviousJobID ::= PreviousJobIDType

PreviousMeterQuantity ::= PreviousMeterQuantityType

PreviousMeterReadingDate ::= PreviousMeterReadingDateType

PreviousVersionID ::= PreviousVersionIDType

PriceAmount ::= PriceAmountType

PriceChangeReason ::= PriceChangeReasonType

PriceEvaluationCode ::= PriceEvaluationCodeType

PriceRevisionFormulaDescription ::= PriceRevisionFormulaDescriptionType

PriceType-1 ::= PriceTypeType

PriceTypeCode ::= PriceTypeCodeType

PricingCurrencyCode ::= PricingCurrencyCodeType

PricingUpdateRequestIndicator ::= PricingUpdateRequestIndicatorType

PrimaryAccountNumberID ::= PrimaryAccountNumberIDType

PrintQualifier ::= PrintQualifierType

Priority ::= PriorityType

PrivacyCode ::= PrivacyCodeType

ProcedureCode ::= ProcedureCodeType

ProcessDescription ::= ProcessDescriptionType

ProcessReason ::= ProcessReasonType

ProcessReasonCode ::= ProcessReasonCodeType

ProcurementProjectLotID ::= ProcurementProjectLotIDType

ProcurementSubTypeCode ::= ProcurementSubTypeCodeType

ProcurementTypeCode ::= ProcurementTypeCodeType

ProductTraceID ::= ProductTraceIDType

ProfileExecutionID ::= ProfileExecutionIDType

ProfileID ::= ProfileIDType

ProfileStatusCode ::= ProfileStatusCodeType

PromotionalEventTypeCode ::= PromotionalEventTypeCodeType

ProviderTypeCode ::= ProviderTypeCodeType

Purpose ::= PurposeType

PurposeCode ::= PurposeCodeType

QualityControlCode ::= QualityControlCodeType

Quantity ::= QuantityType

QuantityDiscrepancyCode ::= QuantityDiscrepancyCodeType

RailCarID ::= RailCarIDType

Rate ::= RateType

ReceivedDate ::= ReceivedDateType

ReceivedQuantity ::= ReceivedQuantityType

ReceivedTenderQuantity ::= ReceivedTenderQuantityType

Reference-1 ::= ReferenceType-1

ReferenceDate ::= ReferenceDateType

ReferenceEventCode ::= ReferenceEventCodeType

ReferenceID ::= ReferenceIDType

ReferenceTime ::= ReferenceTimeType

ReferencedConsignmentID ::= ReferencedConsignmentIDType

RefrigeratedIndicator ::= RefrigeratedIndicatorType

RefrigerationOnIndicator ::= RefrigerationOnIndicatorType

Region ::= RegionType

RegisteredDate ::= RegisteredDateType

RegisteredTime ::= RegisteredTimeType

RegistrationDate ::= RegistrationDateType

RegistrationExpirationDate ::= RegistrationExpirationDateType

RegistrationID ::= RegistrationIDType

RegistrationName ::= RegistrationNameType

RegistrationNationality ::= RegistrationNationalityType

RegistrationNationalityID ::= RegistrationNationalityIDType

RejectActionCode ::= RejectActionCodeType

RejectReason ::= RejectReasonType

RejectReasonCode ::= RejectReasonCodeType

RejectedQuantity ::= RejectedQuantityType

RejectionNote ::= RejectionNoteType

ReleaseID ::= ReleaseIDType

ReliabilityPercent ::= ReliabilityPercentType

Remarks ::= RemarksType

ReminderSequenceNumeric ::= ReminderSequenceNumericType

ReminderTypeCode ::= ReminderTypeCodeType

ReplenishmentOwnerDescription ::= ReplenishmentOwnerDescriptionType

RequestForQuotationLineID ::= RequestForQuotationLineIDType

RequestedDeliveryDate ::= RequestedDeliveryDateType

RequestedDespatchDate ::= RequestedDespatchDateType

RequestedDespatchTime ::= RequestedDespatchTimeType

RequestedInvoiceCurrencyCode ::= RequestedInvoiceCurrencyCodeType

RequestedPublicationDate ::= RequestedPublicationDateType

RequiredCurriculaIndicator ::= RequiredCurriculaIndicatorType

RequiredCustomsID ::= RequiredCustomsIDType

RequiredDeliveryDate ::= RequiredDeliveryDateType

RequiredDeliveryTime ::= RequiredDeliveryTimeType

RequiredFeeAmount ::= RequiredFeeAmountType

ResidenceType ::= ResidenceTypeType

ResidenceTypeCode ::= ResidenceTypeCodeType

ResidentOccupantsNumeric ::= ResidentOccupantsNumericType

Resolution ::= ResolutionType

ResolutionCode ::= ResolutionCodeType

ResolutionDate ::= ResolutionDateType

ResolutionTime ::= ResolutionTimeType

ResponseCode ::= ResponseCodeType

ResponseDate ::= ResponseDateType

ResponseTime ::= ResponseTimeType

RetailEventName ::= RetailEventNameType

RetailEventStatusCode ::= RetailEventStatusCodeType

ReturnabilityIndicator ::= ReturnabilityIndicatorType

ReturnableMaterialIndicator ::= ReturnableMaterialIndicatorType

ReturnableQuantity ::= ReturnableQuantityType

RevisedForecastLineID ::= RevisedForecastLineIDType

RevisionDate ::= RevisionDateType

RevisionStatusCode ::= RevisionStatusCodeType

RevisionTime ::= RevisionTimeType

RoamingPartnerName ::= RoamingPartnerNameType

RoleCode ::= RoleCodeType

Room ::= RoomType

RoundingAmount ::= RoundingAmountType

SalesOrderID ::= SalesOrderIDType

SalesOrderLineID ::= SalesOrderLineIDType

SchemeURI ::= SchemeURIType

SealIssuerTypeCode ::= SealIssuerTypeCodeType

SealStatusCode ::= SealStatusCodeType

SealingPartyType ::= SealingPartyTypeType

SecurityClassificationCode ::= SecurityClassificationCodeType

SecurityID ::= SecurityIDType

SellerEventID ::= SellerEventIDType

SequenceID ::= SequenceIDType

SequenceNumberID ::= SequenceNumberIDType

SequenceNumeric ::= SequenceNumericType

SerialID ::= SerialIDType

ServiceName ::= ServiceNameType

ServiceNumberCalled ::= ServiceNumberCalledType

ServiceType ::= ServiceTypeType

ServiceTypeCode ::= ServiceTypeCodeType

SettlementDiscountAmount ::= SettlementDiscountAmountType

SettlementDiscountPercent ::= SettlementDiscountPercentType

SharesNumberQuantity ::= SharesNumberQuantityType

ShippingMarks ::= ShippingMarksType

ShippingOrderID ::= ShippingOrderIDType

ShippingPriorityLevelCode ::= ShippingPriorityLevelCodeType

ShortQuantity ::= ShortQuantityType

ShortageActionCode ::= ShortageActionCodeType

SignatureID ::= SignatureIDType

SignatureMethod-1 ::= SignatureMethodType-1

SizeTypeCode ::= SizeTypeCodeType

SoleProprietorshipIndicator ::= SoleProprietorshipIndicatorType

SourceCurrencyBaseRate ::= SourceCurrencyBaseRateType

SourceCurrencyCode ::= SourceCurrencyCodeType

SourceForecastIssueDate ::= SourceForecastIssueDateType

SourceForecastIssueTime ::= SourceForecastIssueTimeType

SourceValueMeasure ::= SourceValueMeasureType

SpecialInstructions ::= SpecialInstructionsType

SpecialSecurityIndicator ::= SpecialSecurityIndicatorType

SpecialServiceInstructions ::= SpecialServiceInstructionsType

SpecialTerms ::= SpecialTermsType

SpecialTransportRequirments ::= SpecialTransportRequirmentsType

SpecificationID ::= SpecificationIDType

SpecificationTypeCode ::= SpecificationTypeCodeType

SplitConsignmentIndicator ::= SplitConsignmentIndicatorType

StartDate ::= StartDateType

StartTime ::= StartTimeType

StatementTypeCode ::= StatementTypeCodeType

StatusAvailableIndicator ::= StatusAvailableIndicatorType

StatusCode ::= StatusCodeType

StatusReason ::= StatusReasonType

StatusReasonCode ::= StatusReasonCodeType

StreetName ::= StreetNameType

SubmissionDate ::= SubmissionDateType

SubmissionDueDate ::= SubmissionDueDateType

SubmissionMethodCode ::= SubmissionMethodCodeType

SubscriberID ::= SubscriberIDType-1

SubscriberIDType ::= SubscriberIDTypeType

SubscriberIDTypeCode ::= SubscriberIDTypeCodeType

SubscriberTypeCode ::= SubscriberTypeCodeType

SubscriberTypeIdentifier ::= SubscriberTypeIdentifierType

SubstitutionStatusCode ::= SubstitutionStatusCodeType

SuccessiveSequenceID ::= SuccessiveSequenceIDType

SummaryDescription ::= SummaryDescriptionType

SupplierAssignedAccountID ::= SupplierAssignedAccountIDType

SupplyChainActivityTypeCode ::= SupplyChainActivityTypeCodeType

TareWeightMeasure ::= TareWeightMeasureType

TargetCurrencyBaseRate ::= TargetCurrencyBaseRateType

TargetCurrencyCode ::= TargetCurrencyCodeType

TargetInventoryQuantity ::= TargetInventoryQuantityType

TargetServicePercent ::= TargetServicePercentType

TariffClassCode ::= TariffClassCodeType

TariffCode ::= TariffCodeType

TariffDescription ::= TariffDescriptionType

TaxAmount ::= TaxAmountType

TaxCurrencyCode ::= TaxCurrencyCodeType

TaxEnergyAmount ::= TaxEnergyAmountType

TaxEnergyBalanceAmount ::= TaxEnergyBalanceAmountType

TaxEnergyOnAccountAmount ::= TaxEnergyOnAccountAmountType

TaxEvidenceIndicator ::= TaxEvidenceIndicatorType

TaxExclusiveAmount ::= TaxExclusiveAmountType

TaxExemptionReason ::= TaxExemptionReasonType

TaxExemptionReasonCode ::= TaxExemptionReasonCodeType

TaxIncludedIndicator ::= TaxIncludedIndicatorType

TaxInclusiveAmount ::= TaxInclusiveAmountType

TaxLevelCode ::= TaxLevelCodeType

TaxPointDate ::= TaxPointDateType

TaxTypeCode ::= TaxTypeCodeType

TaxableAmount ::= TaxableAmountType

TechnicalCommitteeDescription ::= TechnicalCommitteeDescriptionType

TechnicalName ::= TechnicalNameType

TelecommunicationsServiceCall ::= TelecommunicationsServiceCallType

TelecommunicationsServiceCallCode ::= TelecommunicationsServiceCallCodeType

TelecommunicationsServiceCategory ::= TelecommunicationsServiceCategoryType

TelecommunicationsServiceCategoryCode ::= 
    TelecommunicationsServiceCategoryCodeType

TelecommunicationsSupplyType-1 ::= TelecommunicationsSupplyTypeType

TelecommunicationsSupplyTypeCode ::= TelecommunicationsSupplyTypeCodeType

Telefax ::= TelefaxType

Telephone ::= TelephoneType

TenderEnvelopeID ::= TenderEnvelopeIDType

TenderEnvelopeTypeCode ::= TenderEnvelopeTypeCodeType

TenderResultCode ::= TenderResultCodeType

TenderTypeCode ::= TenderTypeCodeType

TendererRequirementTypeCode ::= TendererRequirementTypeCodeType

TestMethod ::= TestMethodType

Text ::= TextType

ThirdPartyPayerIndicator ::= ThirdPartyPayerIndicatorType

ThresholdAmount ::= ThresholdAmountType

ThresholdQuantity ::= ThresholdQuantityType

ThresholdValueComparisonCode ::= ThresholdValueComparisonCodeType

TierRange ::= TierRangeType

TierRatePercent ::= TierRatePercentType

TimeAmount ::= TimeAmountType

TimeDeltaDaysQuantity ::= TimeDeltaDaysQuantityType

TimeDeviationIndicator ::= TimeDeviationIndicatorType

TimeFrequencyCode ::= TimeFrequencyCodeType

TimezoneOffset ::= TimezoneOffsetType

TimingComplaint ::= TimingComplaintType

TimingComplaintCode ::= TimingComplaintCodeType

Title ::= TitleType

ToOrderIndicator ::= ToOrderIndicatorType

TotalAmount ::= TotalAmountType

TotalBalanceAmount ::= TotalBalanceAmountType

TotalConsumedQuantity ::= TotalConsumedQuantityType

TotalCreditAmount ::= TotalCreditAmountType

TotalDebitAmount ::= TotalDebitAmountType

TotalDeliveredQuantity ::= TotalDeliveredQuantityType

TotalGoodsItemQuantity ::= TotalGoodsItemQuantityType

TotalInvoiceAmount ::= TotalInvoiceAmountType

TotalMeteredQuantity ::= TotalMeteredQuantityType

TotalPackageQuantity ::= TotalPackageQuantityType

TotalPackagesQuantity ::= TotalPackagesQuantityType

TotalPaymentAmount ::= TotalPaymentAmountType

TotalTaskAmount ::= TotalTaskAmountType

TotalTaxAmount ::= TotalTaxAmountType

TotalTransportHandlingUnitQuantity ::= TotalTransportHandlingUnitQuantityType

TraceID ::= TraceIDType

TrackingDeviceCode ::= TrackingDeviceCodeType

TrackingID ::= TrackingIDType

TradeItemPackingLabelingTypeCode ::= TradeItemPackingLabelingTypeCodeType

TradeServiceCode ::= TradeServiceCodeType

TradingRestrictions ::= TradingRestrictionsType

TrainID ::= TrainIDType

TransactionCurrencyTaxAmount ::= TransactionCurrencyTaxAmountType

TransitDirectionCode ::= TransitDirectionCodeType

TransportAuthorizationCode ::= TransportAuthorizationCodeType

TransportEmergencyCardCode ::= TransportEmergencyCardCodeType

TransportEquipmentTypeCode ::= TransportEquipmentTypeCodeType

TransportEventTypeCode ::= TransportEventTypeCodeType

TransportExecutionPlanReferenceID ::= TransportExecutionPlanReferenceIDType

TransportHandlingUnitTypeCode ::= TransportHandlingUnitTypeCodeType

TransportMeansTypeCode ::= TransportMeansTypeCodeType

TransportModeCode ::= TransportModeCodeType

TransportServiceCode ::= TransportServiceCodeType

TransportServiceProviderCancellationIndicator ::= 
    TransportServiceProviderCancellationIndicatorType

TransportServiceProviderCompletionIndicator ::= 
    TransportServiceProviderCompletionIndicatorType

TransportServiceProviderReadyForExecutionIndicator ::= 
    TransportServiceProviderReadyForExecutionIndicatorType

TransportServiceProviderRemarks ::= TransportServiceProviderRemarksType

TransportServiceProviderSpecialTerms ::= 
    TransportServiceProviderSpecialTermsType

TransportUserCancellationIndicator ::= TransportUserCancellationIndicatorType

TransportUserCompletionIndicator ::= TransportUserCompletionIndicatorType

TransportUserReadyForExecutionIndicator ::= 
    TransportUserReadyForExecutionIndicatorType

TransportUserRemarks ::= TransportUserRemarksType

TransportUserSpecialTerms ::= TransportUserSpecialTermsType

TransportationServiceDescription ::= TransportationServiceDescriptionType

TransportationServiceDetailsURI ::= TransportationServiceDetailsURIType

TypeCode ::= TypeCodeType

UBLVersionID ::= UBLVersionIDType

UNDGCode ::= UNDGCodeType

URI ::= URIType

UUID ::= UUIDType

UnknownPriceIndicator ::= UnknownPriceIndicatorType

UpperOrangeHazardPlacardID ::= UpperOrangeHazardPlacardIDType

UrgencyCode ::= UrgencyCodeType

UtilityStatementTypeCode ::= UtilityStatementTypeCodeType

ValidateProcess ::= ValidateProcessType

ValidateTool ::= ValidateToolType

ValidateToolVersion ::= ValidateToolVersionType

ValidationDate ::= ValidationDateType

ValidationResultCode ::= ValidationResultCodeType

ValidationTime ::= ValidationTimeType

ValidatorID ::= ValidatorIDType

ValidityStartDate ::= ValidityStartDateType

Value ::= ValueType

ValueAmount ::= ValueAmountType

ValueMeasure ::= ValueMeasureType

ValueQualifier ::= ValueQualifierType

ValueQuantity ::= ValueQuantityType

VarianceQuantity ::= VarianceQuantityType

VariantConstraintIndicator ::= VariantConstraintIndicatorType

VariantID ::= VariantIDType

VersionID ::= VersionIDType

VesselID ::= VesselIDType

VesselName ::= VesselNameType

WarrantyInformation ::= WarrantyInformationType

WebsiteURI ::= WebsiteURIType

Weight ::= WeightType

WeightNumeric ::= WeightNumericType

WeightingAlgorithmCode ::= WeightingAlgorithmCodeType

XPath ::= XPathType

AcceptedIndicatorType ::= SEQUENCE {
    base BOOLEAN
}

AcceptedVariantsDescriptionType ::= SEQUENCE {
    languageID       XSD.Language OPTIONAL,
    languageLocaleID XSD.NormalizedString OPTIONAL,
    base             XSD.String
}

AccountFormatCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AccountIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AccountTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AccountingCostCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AccountingCostType ::= SEQUENCE {
    languageID       XSD.Language OPTIONAL,
    languageLocaleID XSD.NormalizedString OPTIONAL,
    base             XSD.String
}

ActionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ActivityCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ActualDeliveryDateType ::= SEQUENCE {
    base XSD.Date
}

ActualDeliveryTimeType ::= SEQUENCE {
    base XSD.Time
}

ActualDespatchDateType ::= SEQUENCE {
    base XSD.Date
}

ActualDespatchTimeType ::= SEQUENCE {
    base XSD.Time
}

ActualPickupDateType ::= SEQUENCE {
    base XSD.Date
}

ActualPickupTimeType ::= SEQUENCE {
    base XSD.Time
}

ActualTemperatureReductionQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

AdValoremIndicatorType ::= SEQUENCE {
    base BOOLEAN
}

AdditionalAccountIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AdditionalInformationType ::= SEQUENCE {
    languageID       XSD.Language OPTIONAL,
    languageLocaleID XSD.NormalizedString OPTIONAL,
    base             XSD.String
}

AdditionalStreetNameType ::= SEQUENCE {
    languageID       XSD.Language OPTIONAL,
    languageLocaleID XSD.NormalizedString OPTIONAL,
    base             XSD.String
}

AddressFormatCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AddressTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AdjustmentReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AdmissionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AdvertisementAmountType ::= SEQUENCE {
    currencyCodeListVersionID XSD.NormalizedString OPTIONAL,
    currencyID   XSD.NormalizedString OPTIONAL,
    base         XSD.Decimal
}

AgencyIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AgencyNameType ::= SEQUENCE {
    languageID       XSD.Language OPTIONAL,
    languageLocaleID XSD.NormalizedString OPTIONAL,
    base             XSD.String
}

AirFlowPercentType ::= SEQUENCE {
    format XSD.String OPTIONAL,
    base   XSD.Decimal
}

AircraftIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AliasNameType ::= SEQUENCE {
    languageID       XSD.Language OPTIONAL,
    languageLocaleID XSD.NormalizedString OPTIONAL,
    base             XSD.String
}

AllowanceChargeReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AllowanceChargeReasonType ::= SEQUENCE {
    languageID       XSD.Language OPTIONAL,
    languageLocaleID XSD.NormalizedString OPTIONAL,
    base             XSD.String
}

AllowanceTotalAmountType ::= SEQUENCE {
    currencyCodeListVersionID XSD.NormalizedString OPTIONAL,
    currencyID   XSD.NormalizedString OPTIONAL,
    base         XSD.Decimal
}

AltitudeMeasureType ::= SEQUENCE {
    unitCode     XSD.NormalizedString OPTIONAL,
    unitCodeListVersionID XSD.NormalizedString OPTIONAL,
    base         XSD.Decimal
}

AmountRateType ::= SEQUENCE {
    format XSD.String OPTIONAL,
    base   XSD.Decimal
}

AmountType ::= SEQUENCE {
    currencyCodeListVersionID XSD.NormalizedString OPTIONAL,
    currencyID   XSD.NormalizedString OPTIONAL,
    base         XSD.Decimal
}

AnimalFoodApprovedIndicatorType ::= SEQUENCE {
    base BOOLEAN
}

AnimalFoodIndicatorType ::= SEQUENCE {
    base BOOLEAN
}

AnnualAverageAmountType ::= SEQUENCE {
    currencyCodeListVersionID XSD.NormalizedString OPTIONAL,
    currencyID   XSD.NormalizedString OPTIONAL,
    base         XSD.Decimal
}

ApplicationStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ApprovalDateType ::= SEQUENCE {
    base XSD.Date
}

ApprovalStatusType ::= SEQUENCE {
    languageID       XSD.Language OPTIONAL,
    languageLocaleID XSD.NormalizedString OPTIONAL,
    base             XSD.String
}

AttributeIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AuctionConstraintIndicatorType ::= SEQUENCE {
    base BOOLEAN
}

AuctionURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AvailabilityDateType ::= SEQUENCE {
    base XSD.Date
}

AvailabilityStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AverageAmountType ::= SEQUENCE {
    currencyCodeListVersionID XSD.NormalizedString OPTIONAL,
    currencyID   XSD.NormalizedString OPTIONAL,
    base         XSD.Decimal
}

AverageSubsequentContractAmountType ::= SEQUENCE {
    currencyCodeListVersionID XSD.NormalizedString OPTIONAL,
    currencyID   XSD.NormalizedString OPTIONAL,
    base         XSD.Decimal
}

AwardDateType ::= SEQUENCE {
    base XSD.Date
}

AwardTimeType ::= SEQUENCE {
    base XSD.Time
}

AwardingCriteriaDescriptionType ::= SEQUENCE {
    languageID       XSD.Language OPTIONAL,
    languageLocaleID XSD.NormalizedString OPTIONAL,
    base             XSD.String
}

AwardingCriteriaIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

AwardingCriteriaTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

AwardingMethodTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

BackOrderAllowedIndicatorType ::= SEQUENCE {
    base BOOLEAN
}

BackorderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

BackorderReasonType ::= SEQUENCE {
    languageID       XSD.Language OPTIONAL,
    languageLocaleID XSD.NormalizedString OPTIONAL,
    base             XSD.String
}

BalanceAmountType ::= SEQUENCE {
    currencyCodeListVersionID XSD.NormalizedString OPTIONAL,
    currencyID   XSD.NormalizedString OPTIONAL,
    base         XSD.Decimal
}

BalanceBroughtForwardIndicatorType ::= SEQUENCE {
    base BOOLEAN
}

BaseAmountType ::= SEQUENCE {
    currencyCodeListVersionID XSD.NormalizedString OPTIONAL,
    currencyID   XSD.NormalizedString OPTIONAL,
    base         XSD.Decimal
}

BaseQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

BaseUnitMeasureType ::= SEQUENCE {
    unitCode     XSD.NormalizedString OPTIONAL,
    unitCodeListVersionID XSD.NormalizedString OPTIONAL,
    base         XSD.Decimal
}

BasedOnConsensusIndicatorType ::= SEQUENCE {
    base BOOLEAN
}

BasicConsumedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

BatchQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

BestBeforeDateType ::= SEQUENCE {
    base XSD.Date
}

BirthDateType ::= SEQUENCE {
    base XSD.Date
}

BlockNameType ::= SEQUENCE {
    languageID       XSD.Language OPTIONAL,
    languageLocaleID XSD.NormalizedString OPTIONAL,
    base             XSD.String
}

BrandNameType ::= SEQUENCE {
    languageID       XSD.Language OPTIONAL,
    languageLocaleID XSD.NormalizedString OPTIONAL,
    base             XSD.String
}

BrokerAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

BudgetYearNumericType ::= SEQUENCE {
    format XSD.String OPTIONAL,
    base   XSD.Decimal
}

BuildingNameType ::= SEQUENCE {
    languageID       XSD.Language OPTIONAL,
    languageLocaleID XSD.NormalizedString OPTIONAL,
    base             XSD.String
}

BuildingNumberType ::= SEQUENCE {
    languageID       XSD.Language OPTIONAL,
    languageLocaleID XSD.NormalizedString OPTIONAL,
    base             XSD.String
}

BulkCargoIndicatorType ::= SEQUENCE {
    base BOOLEAN
}

BusinessClassificationEvidenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

BusinessIdentityEvidenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

BuyerEventIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

BuyerProfileURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CV2IDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CalculationExpressionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CalculationExpressionType ::= SEQUENCE {
    languageID       XSD.Language OPTIONAL,
    languageLocaleID XSD.NormalizedString OPTIONAL,
    base             XSD.String
}

CalculationRateType ::= SEQUENCE {
    format XSD.String OPTIONAL,
    base   XSD.Decimal
}

CalculationSequenceNumericType ::= SEQUENCE {
    format XSD.String OPTIONAL,
    base   XSD.Decimal
}

CallBaseAmountType ::= SEQUENCE {
    currencyCodeListVersionID XSD.NormalizedString OPTIONAL,
    currencyID   XSD.NormalizedString OPTIONAL,
    base         XSD.Decimal
}

CallDateType ::= SEQUENCE {
    base XSD.Date
}

CallExtensionAmountType ::= SEQUENCE {
    currencyCodeListVersionID XSD.NormalizedString OPTIONAL,
    currencyID   XSD.NormalizedString OPTIONAL,
    base         XSD.Decimal
}

CallTimeType ::= SEQUENCE {
    base XSD.Time
}

CancellationNoteType ::= SEQUENCE {
    languageID       XSD.Language OPTIONAL,
    languageLocaleID XSD.NormalizedString OPTIONAL,
    base             XSD.String
}

CandidateReductionConstraintIndicatorType ::= SEQUENCE {
    base BOOLEAN
}

CanonicalizationMethodType-1 ::= SEQUENCE {
    languageID       XSD.Language OPTIONAL,
    languageLocaleID XSD.NormalizedString OPTIONAL,
    base             XSD.String
}

CapabilityTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CardChipCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CardTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CargoTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CarrierAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CarrierServiceInstructionsType ::= SEQUENCE {
    languageID       XSD.Language OPTIONAL,
    languageLocaleID XSD.NormalizedString OPTIONAL,
    base             XSD.String
}

CatalogueIndicatorType ::= SEQUENCE {
    base BOOLEAN
}

CategoryNameType ::= SEQUENCE {
    languageID       XSD.Language OPTIONAL,
    languageLocaleID XSD.NormalizedString OPTIONAL,
    base             XSD.String
}

CertificateTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CertificateTypeType ::= SEQUENCE {
    languageID       XSD.Language OPTIONAL,
    languageLocaleID XSD.NormalizedString OPTIONAL,
    base             XSD.String
}

ChangeConditionsType ::= SEQUENCE {
    languageID       XSD.Language OPTIONAL,
    languageLocaleID XSD.NormalizedString OPTIONAL,
    base             XSD.String
}

ChannelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ChannelType ::= SEQUENCE {
    languageID       XSD.Language OPTIONAL,
    languageLocaleID XSD.NormalizedString OPTIONAL,
    base             XSD.String
}

CharacterSetCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CharacteristicsType ::= SEQUENCE {
    languageID       XSD.Language OPTIONAL,
    languageLocaleID XSD.NormalizedString OPTIONAL,
    base             XSD.String
}

ChargeIndicatorType ::= SEQUENCE {
    base BOOLEAN
}

ChargeTotalAmountType ::= SEQUENCE {
    currencyCodeListVersionID XSD.NormalizedString OPTIONAL,
    currencyID   XSD.NormalizedString OPTIONAL,
    base         XSD.Decimal
}

ChargeableQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ChargeableWeightMeasureType ::= SEQUENCE {
    unitCode     XSD.NormalizedString OPTIONAL,
    unitCodeListVersionID XSD.NormalizedString OPTIONAL,
    base         XSD.Decimal
}

ChipApplicationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CityNameType ::= SEQUENCE {
    languageID       XSD.Language OPTIONAL,
    languageLocaleID XSD.NormalizedString OPTIONAL,
    base             XSD.String
}

CitySubdivisionNameType ::= SEQUENCE {
    languageID       XSD.Language OPTIONAL,
    languageLocaleID XSD.NormalizedString OPTIONAL,
    base             XSD.String
}

ClauseCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ClauseType ::= SEQUENCE {
    languageID       XSD.Language OPTIONAL,
    languageLocaleID XSD.NormalizedString OPTIONAL,
    base             XSD.String
}

CodeValueType ::= SEQUENCE {
    languageID       XSD.Language OPTIONAL,
    languageLocaleID XSD.NormalizedString OPTIONAL,
    base             XSD.String
}

CollaborationPriorityCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CommentType ::= SEQUENCE {
    languageID       XSD.Language OPTIONAL,
    languageLocaleID XSD.NormalizedString OPTIONAL,
    base             XSD.String
}

CommodityCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CompanyIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CompanyLegalFormCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CompanyLiquidationStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ComparedValueMeasureType ::= SEQUENCE {
    unitCode     XSD.NormalizedString OPTIONAL,
    unitCodeListVersionID XSD.NormalizedString OPTIONAL,
    base         XSD.Decimal
}

ComparisonDataCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ComparisonDataSourceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ComparisonForecastIssueDateType ::= SEQUENCE {
    base XSD.Date
}

ComparisonForecastIssueTimeType ::= SEQUENCE {
    base XSD.Time
}

CompletionIndicatorType ::= SEQUENCE {
    base BOOLEAN
}

ConditionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConditionDeviationIndicatorType ::= SEQUENCE {
    base BOOLEAN
}

ConditionType ::= SEQUENCE {
    languageID       XSD.Language OPTIONAL,
    languageLocaleID XSD.NormalizedString OPTIONAL,
    base             XSD.String
}

ConditionValueMeasureType ::= SEQUENCE {
    unitCode     XSD.NormalizedString OPTIONAL,
    unitCodeListVersionID XSD.NormalizedString OPTIONAL,
    base         XSD.Decimal
}

ConditionsDescriptionType ::= SEQUENCE {
    languageID       XSD.Language OPTIONAL,
    languageLocaleID XSD.NormalizedString OPTIONAL,
    base             XSD.String
}

ConditionsType ::= SEQUENCE {
    languageID       XSD.Language OPTIONAL,
    languageLocaleID XSD.NormalizedString OPTIONAL,
    base             XSD.String
}

ConsigneeAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ConsignmentQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ConsignorAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ConsolidatableIndicatorType ::= SEQUENCE {
    base BOOLEAN
}

ConstitutionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConsumerIncentiveTacticTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConsumerUnitQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ConsumersEnergyLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConsumersEnergyLevelType ::= SEQUENCE {
    languageID       XSD.Language OPTIONAL,
    languageLocaleID XSD.NormalizedString OPTIONAL,
    base             XSD.String
}

ConsumptionEnergyQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ConsumptionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ConsumptionLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConsumptionLevelType ::= SEQUENCE {
    languageID       XSD.Language OPTIONAL,
    languageLocaleID XSD.NormalizedString OPTIONAL,
    base             XSD.String
}

ConsumptionReportIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ConsumptionTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ConsumptionTypeType ::= SEQUENCE {
    languageID       XSD.Language OPTIONAL,
    languageLocaleID XSD.NormalizedString OPTIONAL,
    base             XSD.String
}

ConsumptionWaterQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ContainerizedIndicatorType ::= SEQUENCE {
    base BOOLEAN
}

ContentUnitQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ContractFolderIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ContractNameType ::= SEQUENCE {
    languageID       XSD.Language OPTIONAL,
    languageLocaleID XSD.NormalizedString OPTIONAL,
    base             XSD.String
}

ContractSubdivisionType ::= SEQUENCE {
    languageID       XSD.Language OPTIONAL,
    languageLocaleID XSD.NormalizedString OPTIONAL,
    base             XSD.String
}

ContractTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ContractTypeType ::= SEQUENCE {
    languageID       XSD.Language OPTIONAL,
    languageLocaleID XSD.NormalizedString OPTIONAL,
    base             XSD.String
}

ContractedCarrierAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ContractingPartyTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ContractingSystemCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CoordinateSystemCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CopyIndicatorType ::= SEQUENCE {
    base BOOLEAN
}

CorporateRegistrationTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CorporateStockAmountType ::= SEQUENCE {
    currencyCodeListVersionID XSD.NormalizedString OPTIONAL,
    currencyID   XSD.NormalizedString OPTIONAL,
    base         XSD.Decimal
}

CorrectionAmountType ::= SEQUENCE {
    currencyCodeListVersionID XSD.NormalizedString OPTIONAL,
    currencyID   XSD.NormalizedString OPTIONAL,
    base         XSD.Decimal
}

CorrectionTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CorrectionTypeType ::= SEQUENCE {
    languageID       XSD.Language OPTIONAL,
    languageLocaleID XSD.NormalizedString OPTIONAL,
    base             XSD.String
}

CorrectionUnitAmountType ::= SEQUENCE {
    currencyCodeListVersionID XSD.NormalizedString OPTIONAL,
    currencyID   XSD.NormalizedString OPTIONAL,
    base         XSD.Decimal
}

CountrySubentityCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CountrySubentityType ::= SEQUENCE {
    languageID       XSD.Language OPTIONAL,
    languageLocaleID XSD.NormalizedString OPTIONAL,
    base             XSD.String
}

CreditLineAmountType ::= SEQUENCE {
    currencyCodeListVersionID XSD.NormalizedString OPTIONAL,
    currencyID   XSD.NormalizedString OPTIONAL,
    base         XSD.Decimal
}

CreditedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

CurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CurrentChargeTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CurrentChargeTypeType ::= SEQUENCE {
    languageID       XSD.Language OPTIONAL,
    languageLocaleID XSD.NormalizedString OPTIONAL,
    base             XSD.String
}

CustomerAssignedAccountIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CustomerReferenceType ::= SEQUENCE {
    languageID       XSD.Language OPTIONAL,
    languageLocaleID XSD.NormalizedString OPTIONAL,
    base             XSD.String
}

CustomizationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

CustomsClearanceServiceInstructionsType ::= SEQUENCE {
    languageID       XSD.Language OPTIONAL,
    languageLocaleID XSD.NormalizedString OPTIONAL,
    base             XSD.String
}

CustomsImportClassifiedIndicatorType ::= SEQUENCE {
    base BOOLEAN
}

CustomsStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

CustomsTariffQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

DamageRemarksType ::= SEQUENCE {
    languageID       XSD.Language OPTIONAL,
    languageLocaleID XSD.NormalizedString OPTIONAL,
    base             XSD.String
}

DangerousGoodsApprovedIndicatorType ::= SEQUENCE {
    base BOOLEAN
}

DataSendingCapabilityType ::= SEQUENCE {
    languageID       XSD.Language OPTIONAL,
    languageLocaleID XSD.NormalizedString OPTIONAL,
    base             XSD.String
}

DataSourceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DateType ::= SEQUENCE {
    base XSD.Date
}

DebitLineAmountType ::= SEQUENCE {
    currencyCodeListVersionID XSD.NormalizedString OPTIONAL,
    currencyID   XSD.NormalizedString OPTIONAL,
    base         XSD.Decimal
}

DebitedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

DeclarationTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DeclaredCarriageValueAmountType ::= SEQUENCE {
    currencyCodeListVersionID XSD.NormalizedString OPTIONAL,
    currencyID   XSD.NormalizedString OPTIONAL,
    base         XSD.Decimal
}

DeclaredCustomsValueAmountType ::= SEQUENCE {
    currencyCodeListVersionID XSD.NormalizedString OPTIONAL,
    currencyID   XSD.NormalizedString OPTIONAL,
    base         XSD.Decimal
}

DeclaredForCarriageValueAmountType ::= SEQUENCE {
    currencyCodeListVersionID XSD.NormalizedString OPTIONAL,
    currencyID   XSD.NormalizedString OPTIONAL,
    base         XSD.Decimal
}

DeclaredStatisticsValueAmountType ::= SEQUENCE {
    currencyCodeListVersionID XSD.NormalizedString OPTIONAL,
    currencyID   XSD.NormalizedString OPTIONAL,
    base         XSD.Decimal
}

DeliveredQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

DeliveryInstructionsType ::= SEQUENCE {
    languageID       XSD.Language OPTIONAL,
    languageLocaleID XSD.NormalizedString OPTIONAL,
    base             XSD.String
}

DemurrageInstructionsType ::= SEQUENCE {
    languageID       XSD.Language OPTIONAL,
    languageLocaleID XSD.NormalizedString OPTIONAL,
    base             XSD.String
}

DepartmentType ::= SEQUENCE {
    languageID       XSD.Language OPTIONAL,
    languageLocaleID XSD.NormalizedString OPTIONAL,
    base             XSD.String
}

DescriptionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DescriptionType ::= SEQUENCE {
    languageID       XSD.Language OPTIONAL,
    languageLocaleID XSD.NormalizedString OPTIONAL,
    base             XSD.String
}

DespatchAdviceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DifferenceTemperatureReductionQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

DirectionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DisplayTacticTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DispositionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DistrictType ::= SEQUENCE {
    languageID       XSD.Language OPTIONAL,
    languageLocaleID XSD.NormalizedString OPTIONAL,
    base             XSD.String
}

DocumentCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DocumentDescriptionType ::= SEQUENCE {
    languageID       XSD.Language OPTIONAL,
    languageLocaleID XSD.NormalizedString OPTIONAL,
    base             XSD.String
}

DocumentHashType ::= SEQUENCE {
    languageID       XSD.Language OPTIONAL,
    languageLocaleID XSD.NormalizedString OPTIONAL,
    base             XSD.String
}

DocumentIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

DocumentStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DocumentTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DocumentTypeType ::= SEQUENCE {
    languageID       XSD.Language OPTIONAL,
    languageLocaleID XSD.NormalizedString OPTIONAL,
    base             XSD.String
}

DueDateType ::= SEQUENCE {
    base XSD.Date
}

DurationMeasureType ::= SEQUENCE {
    unitCode     XSD.NormalizedString OPTIONAL,
    unitCodeListVersionID XSD.NormalizedString OPTIONAL,
    base         XSD.Decimal
}

DutyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DutyType-1 ::= SEQUENCE {
    languageID       XSD.Language OPTIONAL,
    languageLocaleID XSD.NormalizedString OPTIONAL,
    base             XSD.String
}

EarliestPickupDateType ::= SEQUENCE {
    base XSD.Date
}

EarliestPickupTimeType ::= SEQUENCE {
    base XSD.Time
}

EconomicOperatorRegistryURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

EffectiveDateType ::= SEQUENCE {
    base XSD.Date
}

EffectiveTimeType ::= SEQUENCE {
    base XSD.Time
}

ElectronicDeviceDescriptionType ::= SEQUENCE {
    languageID       XSD.Language OPTIONAL,
    languageLocaleID XSD.NormalizedString OPTIONAL,
    base             XSD.String
}

ElectronicMailType ::= SEQUENCE {
    languageID       XSD.Language OPTIONAL,
    languageLocaleID XSD.NormalizedString OPTIONAL,
    base             XSD.String
}

EmbeddedDocumentBinaryObjectType ::= SEQUENCE {
    characterSetCode XSD.NormalizedString OPTIONAL,
    encodingCode     XSD.NormalizedString OPTIONAL,
    filename         XSD.String OPTIONAL,
    format           XSD.String OPTIONAL,
    mimeCode         XSD.NormalizedString OPTIONAL,
    uri              XSD.AnyURI OPTIONAL,
    base             OCTET STRING
}

EmergencyProceduresCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

EmployeeQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

EncodingCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

EndDateType ::= SEQUENCE {
    base XSD.Date
}

EndTimeType ::= SEQUENCE {
    base XSD.Time
}

EndpointIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

EnvironmentalEmissionTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

EstimatedConsumedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

EstimatedDeliveryDateType ::= SEQUENCE {
    base XSD.Date
}

EstimatedDeliveryTimeType ::= SEQUENCE {
    base XSD.Time
}

EstimatedDespatchDateType ::= SEQUENCE {
    base XSD.Date
}

EstimatedDespatchTimeType ::= SEQUENCE {
    base XSD.Time
}

EstimatedOverallContractAmountType ::= SEQUENCE {
    currencyCodeListVersionID XSD.NormalizedString OPTIONAL,
    currencyID   XSD.NormalizedString OPTIONAL,
    base         XSD.Decimal
}

EstimatedOverallContractQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

EvaluationCriteriaTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

EvidenceSuppliedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

EvidenceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExceptionResolutionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExceptionStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExchangeMarketIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ExclusionReasonType ::= SEQUENCE {
    languageID       XSD.Language OPTIONAL,
    languageLocaleID XSD.NormalizedString OPTIONAL,
    base             XSD.String
}

ExecutionRequirementCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExemptionReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExemptionReasonType ::= SEQUENCE {
    languageID       XSD.Language OPTIONAL,
    languageLocaleID XSD.NormalizedString OPTIONAL,
    base             XSD.String
}

ExpectedOperatorQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ExpectedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ExpenseCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExpiryDateType ::= SEQUENCE {
    base XSD.Date
}

ExpiryTimeType ::= SEQUENCE {
    base XSD.Time
}

ExpressionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ExtendedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ExtensionType ::= SEQUENCE {
    languageID       XSD.Language OPTIONAL,
    languageLocaleID XSD.NormalizedString OPTIONAL,
    base             XSD.String
}

FaceValueAmountType ::= SEQUENCE {
    currencyCodeListVersionID XSD.NormalizedString OPTIONAL,
    currencyID   XSD.NormalizedString OPTIONAL,
    base         XSD.Decimal
}

FamilyNameType ::= SEQUENCE {
    languageID       XSD.Language OPTIONAL,
    languageLocaleID XSD.NormalizedString OPTIONAL,
    base             XSD.String
}

FeatureTacticTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FeeAmountType ::= SEQUENCE {
    currencyCodeListVersionID XSD.NormalizedString OPTIONAL,
    currencyID   XSD.NormalizedString OPTIONAL,
    base         XSD.Decimal
}

FeeDescriptionType ::= SEQUENCE {
    languageID       XSD.Language OPTIONAL,
    languageLocaleID XSD.NormalizedString OPTIONAL,
    base             XSD.String
}

FileNameType ::= SEQUENCE {
    languageID       XSD.Language OPTIONAL,
    languageLocaleID XSD.NormalizedString OPTIONAL,
    base             XSD.String
}

FinancingInstrumentCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FirstNameType ::= SEQUENCE {
    languageID       XSD.Language OPTIONAL,
    languageLocaleID XSD.NormalizedString OPTIONAL,
    base             XSD.String
}

FirstShipmentAvailibilityDateType ::= SEQUENCE {
    base XSD.Date
}

FloorType ::= SEQUENCE {
    languageID       XSD.Language OPTIONAL,
    languageLocaleID XSD.NormalizedString OPTIONAL,
    base             XSD.String
}

ForecastPurposeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ForecastTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FormatCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ForwarderServiceInstructionsType ::= SEQUENCE {
    languageID       XSD.Language OPTIONAL,
    languageLocaleID XSD.NormalizedString OPTIONAL,
    base             XSD.String
}

FreeOfChargeIndicatorType ::= SEQUENCE {
    base BOOLEAN
}

FreeOnBoardValueAmountType ::= SEQUENCE {
    currencyCodeListVersionID XSD.NormalizedString OPTIONAL,
    currencyID   XSD.NormalizedString OPTIONAL,
    base         XSD.Decimal
}

FreightForwarderAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

FreightRateClassCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FrequencyType ::= SEQUENCE {
    languageID       XSD.Language OPTIONAL,
    languageLocaleID XSD.NormalizedString OPTIONAL,
    base             XSD.String
}

FrozenDocumentIndicatorType ::= SEQUENCE {
    base BOOLEAN
}

FrozenPeriodDaysNumericType ::= SEQUENCE {
    format XSD.String OPTIONAL,
    base   XSD.Decimal
}

FullnessIndicationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FullyPaidSharesIndicatorType ::= SEQUENCE {
    base BOOLEAN
}

FundingProgramCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

FundingProgramType ::= SEQUENCE {
    languageID       XSD.Language OPTIONAL,
    languageLocaleID XSD.NormalizedString OPTIONAL,
    base             XSD.String
}

GasPressureQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

GenderCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

GeneralCargoIndicatorType ::= SEQUENCE {
    base BOOLEAN
}

GovernmentAgreementConstraintIndicatorType ::= SEQUENCE {
    base BOOLEAN
}

GrossVolumeMeasureType ::= SEQUENCE {
    unitCode     XSD.NormalizedString OPTIONAL,
    unitCodeListVersionID XSD.NormalizedString OPTIONAL,
    base         XSD.Decimal
}

GrossWeightMeasureType ::= SEQUENCE {
    unitCode     XSD.NormalizedString OPTIONAL,
    unitCodeListVersionID XSD.NormalizedString OPTIONAL,
    base         XSD.Decimal
}

GuaranteeTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

GuaranteedDespatchDateType ::= SEQUENCE {
    base XSD.Date
}

GuaranteedDespatchTimeType ::= SEQUENCE {
    base XSD.Time
}

HandlingCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

HandlingInstructionsType ::= SEQUENCE {
    languageID       XSD.Language OPTIONAL,
    languageLocaleID XSD.NormalizedString OPTIONAL,
    base             XSD.String
}

HashAlgorithmMethodType ::= SEQUENCE {
    languageID       XSD.Language OPTIONAL,
    languageLocaleID XSD.NormalizedString OPTIONAL,
    base             XSD.String
}

HaulageInstructionsType ::= SEQUENCE {
    languageID       XSD.Language OPTIONAL,
    languageLocaleID XSD.NormalizedString OPTIONAL,
    base             XSD.String
}

HazardClassIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

HazardousCategoryCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

HazardousRegulationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

HazardousRiskIndicatorType ::= SEQUENCE {
    base BOOLEAN
}

HeatingTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

HeatingTypeType ::= SEQUENCE {
    languageID       XSD.Language OPTIONAL,
    languageLocaleID XSD.NormalizedString OPTIONAL,
    base             XSD.String
}

HigherTenderAmountType ::= SEQUENCE {
    currencyCodeListVersionID XSD.NormalizedString OPTIONAL,
    currencyID   XSD.NormalizedString OPTIONAL,
    base         XSD.Decimal
}

HolderNameType ::= SEQUENCE {
    languageID       XSD.Language OPTIONAL,
    languageLocaleID XSD.NormalizedString OPTIONAL,
    base             XSD.String
}

HumanFoodApprovedIndicatorType ::= SEQUENCE {
    base BOOLEAN
}

HumanFoodIndicatorType ::= SEQUENCE {
    base BOOLEAN
}

HumidityPercentType ::= SEQUENCE {
    format XSD.String OPTIONAL,
    base   XSD.Decimal
}

IDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

IdentificationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

IdentificationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ImmobilizationCertificateIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ImportanceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

IndicationIndicatorType ::= SEQUENCE {
    base BOOLEAN
}

IndustryClassificationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

InformationType ::= SEQUENCE {
    languageID       XSD.Language OPTIONAL,
    languageLocaleID XSD.NormalizedString OPTIONAL,
    base             XSD.String
}

InformationURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

InhalationToxicityZoneCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

InhouseMailType ::= SEQUENCE {
    languageID       XSD.Language OPTIONAL,
    languageLocaleID XSD.NormalizedString OPTIONAL,
    base             XSD.String
}

InspectionMethodCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

InstallmentDueDateType ::= SEQUENCE {
    base XSD.Date
}

InstructionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

InstructionNoteType ::= SEQUENCE {
    languageID       XSD.Language OPTIONAL,
    languageLocaleID XSD.NormalizedString OPTIONAL,
    base             XSD.String
}

InstructionsType ::= SEQUENCE {
    languageID       XSD.Language OPTIONAL,
    languageLocaleID XSD.NormalizedString OPTIONAL,
    base             XSD.String
}

InsurancePremiumAmountType ::= SEQUENCE {
    currencyCodeListVersionID XSD.NormalizedString OPTIONAL,
    currencyID   XSD.NormalizedString OPTIONAL,
    base         XSD.Decimal
}

InsuranceValueAmountType ::= SEQUENCE {
    currencyCodeListVersionID XSD.NormalizedString OPTIONAL,
    currencyID   XSD.NormalizedString OPTIONAL,
    base         XSD.Decimal
}

InterestedProcurementLotsIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

InventoryValueAmountType ::= SEQUENCE {
    currencyCodeListVersionID XSD.NormalizedString OPTIONAL,
    currencyID   XSD.NormalizedString OPTIONAL,
    base         XSD.Decimal
}

InvoiceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

InvoicedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

InvoicingPartyReferenceType ::= SEQUENCE {
    languageID       XSD.Language OPTIONAL,
    languageLocaleID XSD.NormalizedString OPTIONAL,
    base             XSD.String
}

IssueDateType ::= SEQUENCE {
    base XSD.Date
}

IssueNumberIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

IssueTimeType ::= SEQUENCE {
    base XSD.Time
}

IssuerIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ItemClassificationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ItemUpdateRequestIndicatorType ::= SEQUENCE {
    base BOOLEAN
}

JobTitleType ::= SEQUENCE {
    languageID       XSD.Language OPTIONAL,
    languageLocaleID XSD.NormalizedString OPTIONAL,
    base             XSD.String
}

JourneyIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

JustificationDescriptionType ::= SEQUENCE {
    languageID       XSD.Language OPTIONAL,
    languageLocaleID XSD.NormalizedString OPTIONAL,
    base             XSD.String
}

JustificationType ::= SEQUENCE {
    languageID       XSD.Language OPTIONAL,
    languageLocaleID XSD.NormalizedString OPTIONAL,
    base             XSD.String
}

KeywordType ::= SEQUENCE {
    languageID       XSD.Language OPTIONAL,
    languageLocaleID XSD.NormalizedString OPTIONAL,
    base             XSD.String
}

LanguageIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LastRevisionDateType ::= SEQUENCE {
    base XSD.Date
}

LastRevisionTimeType ::= SEQUENCE {
    base XSD.Time
}

LatestDeliveryDateType ::= SEQUENCE {
    base XSD.Date
}

LatestDeliveryTimeType ::= SEQUENCE {
    base XSD.Time
}

LatestMeterQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

LatestMeterReadingDateType ::= SEQUENCE {
    base XSD.Date
}

LatestPickupDateType ::= SEQUENCE {
    base XSD.Date
}

LatestPickupTimeType ::= SEQUENCE {
    base XSD.Time
}

LatestProposalAcceptanceDateType ::= SEQUENCE {
    base XSD.Date
}

LatitudeDegreesMeasureType ::= SEQUENCE {
    unitCode     XSD.NormalizedString OPTIONAL,
    unitCodeListVersionID XSD.NormalizedString OPTIONAL,
    base         XSD.Decimal
}

LatitudeDirectionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LatitudeMinutesMeasureType ::= SEQUENCE {
    unitCode     XSD.NormalizedString OPTIONAL,
    unitCodeListVersionID XSD.NormalizedString OPTIONAL,
    base         XSD.Decimal
}

LeadTimeMeasureType ::= SEQUENCE {
    unitCode     XSD.NormalizedString OPTIONAL,
    unitCodeListVersionID XSD.NormalizedString OPTIONAL,
    base         XSD.Decimal
}

LegalFormType ::= SEQUENCE {
    languageID       XSD.Language OPTIONAL,
    languageLocaleID XSD.NormalizedString OPTIONAL,
    base             XSD.String
}

LegalReferenceType ::= SEQUENCE {
    languageID       XSD.Language OPTIONAL,
    languageLocaleID XSD.NormalizedString OPTIONAL,
    base             XSD.String
}

LegalStatusIndicatorType ::= SEQUENCE {
    base BOOLEAN
}

LiabilityAmountType ::= SEQUENCE {
    currencyCodeListVersionID XSD.NormalizedString OPTIONAL,
    currencyID   XSD.NormalizedString OPTIONAL,
    base         XSD.Decimal
}

LicensePlateIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LifeCycleStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LimitationDescriptionType ::= SEQUENCE {
    languageID       XSD.Language OPTIONAL,
    languageLocaleID XSD.NormalizedString OPTIONAL,
    base             XSD.String
}

LineCountNumericType ::= SEQUENCE {
    format XSD.String OPTIONAL,
    base   XSD.Decimal
}

LineExtensionAmountType ::= SEQUENCE {
    currencyCodeListVersionID XSD.NormalizedString OPTIONAL,
    currencyID   XSD.NormalizedString OPTIONAL,
    base         XSD.Decimal
}

LineIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LineNumberNumericType ::= SEQUENCE {
    format XSD.String OPTIONAL,
    base   XSD.Decimal
}

LineStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LineType ::= SEQUENCE {
    languageID       XSD.Language OPTIONAL,
    languageLocaleID XSD.NormalizedString OPTIONAL,
    base             XSD.String
}

ListValueType ::= SEQUENCE {
    languageID       XSD.Language OPTIONAL,
    languageLocaleID XSD.NormalizedString OPTIONAL,
    base             XSD.String
}

LivestockIndicatorType ::= SEQUENCE {
    base BOOLEAN
}

LoadingLengthMeasureType ::= SEQUENCE {
    unitCode     XSD.NormalizedString OPTIONAL,
    unitCodeListVersionID XSD.NormalizedString OPTIONAL,
    base         XSD.Decimal
}

LoadingSequenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LocaleCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LocationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LocationType-1 ::= SEQUENCE {
    languageID       XSD.Language OPTIONAL,
    languageLocaleID XSD.NormalizedString OPTIONAL,
    base             XSD.String
}

LocationTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LoginType ::= SEQUENCE {
    languageID       XSD.Language OPTIONAL,
    languageLocaleID XSD.NormalizedString OPTIONAL,
    base             XSD.String
}

LogoReferenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LongitudeDegreesMeasureType ::= SEQUENCE {
    unitCode     XSD.NormalizedString OPTIONAL,
    unitCodeListVersionID XSD.NormalizedString OPTIONAL,
    base         XSD.Decimal
}

LongitudeDirectionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LongitudeMinutesMeasureType ::= SEQUENCE {
    unitCode     XSD.NormalizedString OPTIONAL,
    unitCodeListVersionID XSD.NormalizedString OPTIONAL,
    base         XSD.Decimal
}

LossRiskResponsibilityCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

LossRiskType ::= SEQUENCE {
    languageID       XSD.Language OPTIONAL,
    languageLocaleID XSD.NormalizedString OPTIONAL,
    base             XSD.String
}

LotNumberIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LowTendersDescriptionType ::= SEQUENCE {
    languageID       XSD.Language OPTIONAL,
    languageLocaleID XSD.NormalizedString OPTIONAL,
    base             XSD.String
}

LowerOrangeHazardPlacardIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

LowerTenderAmountType ::= SEQUENCE {
    currencyCodeListVersionID XSD.NormalizedString OPTIONAL,
    currencyID   XSD.NormalizedString OPTIONAL,
    base         XSD.Decimal
}

MandateTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ManufactureDateType ::= SEQUENCE {
    base XSD.Date
}

ManufactureTimeType ::= SEQUENCE {
    base XSD.Time
}

MarkAttentionIndicatorType ::= SEQUENCE {
    base BOOLEAN
}

MarkAttentionType ::= SEQUENCE {
    languageID       XSD.Language OPTIONAL,
    languageLocaleID XSD.NormalizedString OPTIONAL,
    base             XSD.String
}

MarkCareIndicatorType ::= SEQUENCE {
    base BOOLEAN
}

MarkCareType ::= SEQUENCE {
    languageID       XSD.Language OPTIONAL,
    languageLocaleID XSD.NormalizedString OPTIONAL,
    base             XSD.String
}

MarketValueAmountType ::= SEQUENCE {
    currencyCodeListVersionID XSD.NormalizedString OPTIONAL,
    currencyID   XSD.NormalizedString OPTIONAL,
    base         XSD.Decimal
}

MarkingIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

MathematicOperatorCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MaximumAdvertisementAmountType ::= SEQUENCE {
    currencyCodeListVersionID XSD.NormalizedString OPTIONAL,
    currencyID   XSD.NormalizedString OPTIONAL,
    base         XSD.Decimal
}

MaximumAmountType ::= SEQUENCE {
    currencyCodeListVersionID XSD.NormalizedString OPTIONAL,
    currencyID   XSD.NormalizedString OPTIONAL,
    base         XSD.Decimal
}

MaximumBackorderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MaximumCopiesNumericType ::= SEQUENCE {
    format XSD.String OPTIONAL,
    base   XSD.Decimal
}

MaximumMeasureType ::= SEQUENCE {
    unitCode     XSD.NormalizedString OPTIONAL,
    unitCodeListVersionID XSD.NormalizedString OPTIONAL,
    base         XSD.Decimal
}

MaximumNumberNumericType ::= SEQUENCE {
    format XSD.String OPTIONAL,
    base   XSD.Decimal
}

MaximumOperatorQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MaximumOrderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MaximumPaidAmountType ::= SEQUENCE {
    currencyCodeListVersionID XSD.NormalizedString OPTIONAL,
    currencyID   XSD.NormalizedString OPTIONAL,
    base         XSD.Decimal
}

MaximumPaymentInstructionsNumericType ::= SEQUENCE {
    format XSD.String OPTIONAL,
    base   XSD.Decimal
}

MaximumQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MaximumTaxExclusiveAmountType ::= SEQUENCE {
    currencyCodeListVersionID XSD.NormalizedString OPTIONAL,
    currencyID   XSD.NormalizedString OPTIONAL,
    base         XSD.Decimal
}

MaximumTaxInclusiveAmountType ::= SEQUENCE {
    currencyCodeListVersionID XSD.NormalizedString OPTIONAL,
    currencyID   XSD.NormalizedString OPTIONAL,
    base         XSD.Decimal
}

MaximumValueType ::= SEQUENCE {
    languageID       XSD.Language OPTIONAL,
    languageLocaleID XSD.NormalizedString OPTIONAL,
    base             XSD.String
}

MaximumVariantQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MeasureType ::= SEQUENCE {
    unitCode     XSD.NormalizedString OPTIONAL,
    unitCodeListVersionID XSD.NormalizedString OPTIONAL,
    base         XSD.Decimal
}

MedicalFirstAidGuideCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MeterConstantCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MeterConstantType ::= SEQUENCE {
    languageID       XSD.Language OPTIONAL,
    languageLocaleID XSD.NormalizedString OPTIONAL,
    base             XSD.String
}

MeterNameType ::= SEQUENCE {
    languageID       XSD.Language OPTIONAL,
    languageLocaleID XSD.NormalizedString OPTIONAL,
    base             XSD.String
}

MeterNumberType ::= SEQUENCE {
    languageID       XSD.Language OPTIONAL,
    languageLocaleID XSD.NormalizedString OPTIONAL,
    base             XSD.String
}

MeterReadingCommentsType ::= SEQUENCE {
    languageID       XSD.Language OPTIONAL,
    languageLocaleID XSD.NormalizedString OPTIONAL,
    base             XSD.String
}

MeterReadingMethodCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MeterReadingMethodType ::= SEQUENCE {
    languageID       XSD.Language OPTIONAL,
    languageLocaleID XSD.NormalizedString OPTIONAL,
    base             XSD.String
}

MeterReadingTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MeterReadingTypeType ::= SEQUENCE {
    languageID       XSD.Language OPTIONAL,
    languageLocaleID XSD.NormalizedString OPTIONAL,
    base             XSD.String
}

MiddleNameType ::= SEQUENCE {
    languageID       XSD.Language OPTIONAL,
    languageLocaleID XSD.NormalizedString OPTIONAL,
    base             XSD.String
}

MimeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

MinimumAmountType ::= SEQUENCE {
    currencyCodeListVersionID XSD.NormalizedString OPTIONAL,
    currencyID   XSD.NormalizedString OPTIONAL,
    base         XSD.Decimal
}

MinimumBackorderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MinimumImprovementBidType ::= SEQUENCE {
    languageID       XSD.Language OPTIONAL,
    languageLocaleID XSD.NormalizedString OPTIONAL,
    base             XSD.String
}

MinimumInventoryQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MinimumMeasureType ::= SEQUENCE {
    unitCode     XSD.NormalizedString OPTIONAL,
    unitCodeListVersionID XSD.NormalizedString OPTIONAL,
    base         XSD.Decimal
}

MinimumNumberNumericType ::= SEQUENCE {
    format XSD.String OPTIONAL,
    base   XSD.Decimal
}

MinimumOrderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MinimumQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MinimumValueType ::= SEQUENCE {
    languageID       XSD.Language OPTIONAL,
    languageLocaleID XSD.NormalizedString OPTIONAL,
    base             XSD.String
}

MiscellaneousEventTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ModelNameType ::= SEQUENCE {
    languageID       XSD.Language OPTIONAL,
    languageLocaleID XSD.NormalizedString OPTIONAL,
    base             XSD.String
}

MonetaryScopeType ::= SEQUENCE {
    languageID       XSD.Language OPTIONAL,
    languageLocaleID XSD.NormalizedString OPTIONAL,
    base             XSD.String
}

MovieTitleType ::= SEQUENCE {
    languageID       XSD.Language OPTIONAL,
    languageLocaleID XSD.NormalizedString OPTIONAL,
    base             XSD.String
}

MultipleOrderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

MultiplierFactorNumericType ::= SEQUENCE {
    format XSD.String OPTIONAL,
    base   XSD.Decimal
}

NameCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

NameSuffixType ::= SEQUENCE {
    languageID       XSD.Language OPTIONAL,
    languageLocaleID XSD.NormalizedString OPTIONAL,
    base             XSD.String
}

NameType ::= SEQUENCE {
    languageID       XSD.Language OPTIONAL,
    languageLocaleID XSD.NormalizedString OPTIONAL,
    base             XSD.String
}

NationalityIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

NatureCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

NegotiationDescriptionType ::= SEQUENCE {
    languageID       XSD.Language OPTIONAL,
    languageLocaleID XSD.NormalizedString OPTIONAL,
    base             XSD.String
}

NetNetWeightMeasureType ::= SEQUENCE {
    unitCode     XSD.NormalizedString OPTIONAL,
    unitCodeListVersionID XSD.NormalizedString OPTIONAL,
    base         XSD.Decimal
}

NetVolumeMeasureType ::= SEQUENCE {
    unitCode     XSD.NormalizedString OPTIONAL,
    unitCodeListVersionID XSD.NormalizedString OPTIONAL,
    base         XSD.Decimal
}

NetWeightMeasureType ::= SEQUENCE {
    unitCode     XSD.NormalizedString OPTIONAL,
    unitCodeListVersionID XSD.NormalizedString OPTIONAL,
    base         XSD.Decimal
}

NetworkIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

NominationDateType ::= SEQUENCE {
    base XSD.Date
}

NominationTimeType ::= SEQUENCE {
    base XSD.Time
}

NormalTemperatureReductionQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

NoteType ::= SEQUENCE {
    languageID       XSD.Language OPTIONAL,
    languageLocaleID XSD.NormalizedString OPTIONAL,
    base             XSD.String
}

NotificationTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

OccurrenceDateType ::= SEQUENCE {
    base XSD.Date
}

OccurrenceTimeType ::= SEQUENCE {
    base XSD.Time
}

OnCarriageIndicatorType ::= SEQUENCE {
    base BOOLEAN
}

OneTimeChargeTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

OneTimeChargeTypeType ::= SEQUENCE {
    languageID       XSD.Language OPTIONAL,
    languageLocaleID XSD.NormalizedString OPTIONAL,
    base             XSD.String
}

OntologyURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

OpenTenderIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

OperatingYearsQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

OperationStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

OptionalLineItemIndicatorType ::= SEQUENCE {
    base BOOLEAN
}

OptionsDescriptionType ::= SEQUENCE {
    languageID       XSD.Language OPTIONAL,
    languageLocaleID XSD.NormalizedString OPTIONAL,
    base             XSD.String
}

OrderIntervalDaysNumericType ::= SEQUENCE {
    format XSD.String OPTIONAL,
    base   XSD.Decimal
}

OrderQuantityIncrementNumericType ::= SEQUENCE {
    format XSD.String OPTIONAL,
    base   XSD.Decimal
}

OrderResponseCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

OrderTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

OrderableIndicatorType ::= SEQUENCE {
    base BOOLEAN
}

OrderableUnitFactorRateType ::= SEQUENCE {
    format XSD.String OPTIONAL,
    base   XSD.Decimal
}

OrderableUnitType ::= SEQUENCE {
    languageID       XSD.Language OPTIONAL,
    languageLocaleID XSD.NormalizedString OPTIONAL,
    base             XSD.String
}

OrganizationDepartmentType ::= SEQUENCE {
    languageID       XSD.Language OPTIONAL,
    languageLocaleID XSD.NormalizedString OPTIONAL,
    base             XSD.String
}

OriginalContractingSystemIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

OriginalJobIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

OtherInstructionType ::= SEQUENCE {
    languageID       XSD.Language OPTIONAL,
    languageLocaleID XSD.NormalizedString OPTIONAL,
    base             XSD.String
}

OutstandingQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

OutstandingReasonType ::= SEQUENCE {
    languageID       XSD.Language OPTIONAL,
    languageLocaleID XSD.NormalizedString OPTIONAL,
    base             XSD.String
}

OversupplyQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

OwnerTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PackLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PackQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

PackSizeNumericType ::= SEQUENCE {
    format XSD.String OPTIONAL,
    base   XSD.Decimal
}

PackageLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PackagingTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PackingCriteriaCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PackingMaterialType ::= SEQUENCE {
    languageID       XSD.Language OPTIONAL,
    languageLocaleID XSD.NormalizedString OPTIONAL,
    base             XSD.String
}

PaidAmountType ::= SEQUENCE {
    currencyCodeListVersionID XSD.NormalizedString OPTIONAL,
    currencyID   XSD.NormalizedString OPTIONAL,
    base         XSD.Decimal
}

PaidDateType ::= SEQUENCE {
    base XSD.Date
}

PaidTimeType ::= SEQUENCE {
    base XSD.Time
}

ParentDocumentIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ParentDocumentLineReferenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ParentDocumentTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ParentDocumentVersionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PartPresentationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PartecipationPercentType ::= SEQUENCE {
    format XSD.String OPTIONAL,
    base   XSD.Decimal
}

PartialDeliveryIndicatorType ::= SEQUENCE {
    base BOOLEAN
}

ParticipationPercentType ::= SEQUENCE {
    format XSD.String OPTIONAL,
    base   XSD.Decimal
}

PartyCapacityAmountType ::= SEQUENCE {
    currencyCodeListVersionID XSD.NormalizedString OPTIONAL,
    currencyID   XSD.NormalizedString OPTIONAL,
    base         XSD.Decimal
}

PasswordType ::= SEQUENCE {
    languageID       XSD.Language OPTIONAL,
    languageLocaleID XSD.NormalizedString OPTIONAL,
    base             XSD.String
}

PayPerViewType ::= SEQUENCE {
    languageID       XSD.Language OPTIONAL,
    languageLocaleID XSD.NormalizedString OPTIONAL,
    base             XSD.String
}

PayableAlternativeAmountType ::= SEQUENCE {
    currencyCodeListVersionID XSD.NormalizedString OPTIONAL,
    currencyID   XSD.NormalizedString OPTIONAL,
    base         XSD.Decimal
}

PayableAmountType ::= SEQUENCE {
    currencyCodeListVersionID XSD.NormalizedString OPTIONAL,
    currencyID   XSD.NormalizedString OPTIONAL,
    base         XSD.Decimal
}

PayableRoundingAmountType ::= SEQUENCE {
    currencyCodeListVersionID XSD.NormalizedString OPTIONAL,
    currencyID   XSD.NormalizedString OPTIONAL,
    base         XSD.Decimal
}

PayerReferenceType ::= SEQUENCE {
    languageID       XSD.Language OPTIONAL,
    languageLocaleID XSD.NormalizedString OPTIONAL,
    base             XSD.String
}

PaymentAlternativeCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentChannelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentDueDateType ::= SEQUENCE {
    base XSD.Date
}

PaymentFrequencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PaymentMeansCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentMeansIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PaymentNoteType ::= SEQUENCE {
    languageID       XSD.Language OPTIONAL,
    languageLocaleID XSD.NormalizedString OPTIONAL,
    base             XSD.String
}

PaymentOrderReferenceType ::= SEQUENCE {
    languageID       XSD.Language OPTIONAL,
    languageLocaleID XSD.NormalizedString OPTIONAL,
    base             XSD.String
}

PaymentPercentType ::= SEQUENCE {
    format XSD.String OPTIONAL,
    base   XSD.Decimal
}

PaymentPurposeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PaymentTermsDetailsURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PenaltyAmountType ::= SEQUENCE {
    currencyCodeListVersionID XSD.NormalizedString OPTIONAL,
    currencyID   XSD.NormalizedString OPTIONAL,
    base         XSD.Decimal
}

PenaltyClausesType ::= SEQUENCE {
    languageID       XSD.Language OPTIONAL,
    languageLocaleID XSD.NormalizedString OPTIONAL,
    base             XSD.String
}

PenaltySurchargePercentType ::= SEQUENCE {
    format XSD.String OPTIONAL,
    base   XSD.Decimal
}

PerUnitAmountType ::= SEQUENCE {
    currencyCodeListVersionID XSD.NormalizedString OPTIONAL,
    currencyID   XSD.NormalizedString OPTIONAL,
    base         XSD.Decimal
}

PercentType ::= SEQUENCE {
    format XSD.String OPTIONAL,
    base   XSD.Decimal
}

PerformanceMetricTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PerformanceValueQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

PerformingCarrierAssignedIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PersonalSituationType ::= SEQUENCE {
    languageID       XSD.Language OPTIONAL,
    languageLocaleID XSD.NormalizedString OPTIONAL,
    base             XSD.String
}

PhoneNumberType ::= SEQUENCE {
    languageID       XSD.Language OPTIONAL,
    languageLocaleID XSD.NormalizedString OPTIONAL,
    base             XSD.String
}

PlacardEndorsementType ::= SEQUENCE {
    languageID       XSD.Language OPTIONAL,
    languageLocaleID XSD.NormalizedString OPTIONAL,
    base             XSD.String
}

PlacardNotationType ::= SEQUENCE {
    languageID       XSD.Language OPTIONAL,
    languageLocaleID XSD.NormalizedString OPTIONAL,
    base             XSD.String
}

PlannedDateType ::= SEQUENCE {
    base XSD.Date
}

PlotIdentificationType ::= SEQUENCE {
    languageID       XSD.Language OPTIONAL,
    languageLocaleID XSD.NormalizedString OPTIONAL,
    base             XSD.String
}

PositionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PostalZoneType ::= SEQUENCE {
    languageID       XSD.Language OPTIONAL,
    languageLocaleID XSD.NormalizedString OPTIONAL,
    base             XSD.String
}

PostboxType ::= SEQUENCE {
    languageID       XSD.Language OPTIONAL,
    languageLocaleID XSD.NormalizedString OPTIONAL,
    base             XSD.String
}

PowerIndicatorType ::= SEQUENCE {
    base BOOLEAN
}

PreCarriageIndicatorType ::= SEQUENCE {
    base BOOLEAN
}

PreferenceCriterionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PrepaidAmountType ::= SEQUENCE {
    currencyCodeListVersionID XSD.NormalizedString OPTIONAL,
    currencyID   XSD.NormalizedString OPTIONAL,
    base         XSD.Decimal
}

PrepaidIndicatorType ::= SEQUENCE {
    base BOOLEAN
}

PrepaidPaymentReferenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PreviousCancellationReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PreviousJobIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PreviousMeterQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

PreviousMeterReadingDateType ::= SEQUENCE {
    base XSD.Date
}

PreviousVersionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PriceAmountType ::= SEQUENCE {
    currencyCodeListVersionID XSD.NormalizedString OPTIONAL,
    currencyID   XSD.NormalizedString OPTIONAL,
    base         XSD.Decimal
}

PriceChangeReasonType ::= SEQUENCE {
    languageID       XSD.Language OPTIONAL,
    languageLocaleID XSD.NormalizedString OPTIONAL,
    base             XSD.String
}

PriceEvaluationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PriceRevisionFormulaDescriptionType ::= SEQUENCE {
    languageID       XSD.Language OPTIONAL,
    languageLocaleID XSD.NormalizedString OPTIONAL,
    base             XSD.String
}

PriceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PriceTypeType ::= SEQUENCE {
    languageID       XSD.Language OPTIONAL,
    languageLocaleID XSD.NormalizedString OPTIONAL,
    base             XSD.String
}

PricingCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PricingUpdateRequestIndicatorType ::= SEQUENCE {
    base BOOLEAN
}

PrimaryAccountNumberIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

PrintQualifierType ::= SEQUENCE {
    languageID       XSD.Language OPTIONAL,
    languageLocaleID XSD.NormalizedString OPTIONAL,
    base             XSD.String
}

PriorityType ::= SEQUENCE {
    languageID       XSD.Language OPTIONAL,
    languageLocaleID XSD.NormalizedString OPTIONAL,
    base             XSD.String
}

PrivacyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProcedureCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProcessDescriptionType ::= SEQUENCE {
    languageID       XSD.Language OPTIONAL,
    languageLocaleID XSD.NormalizedString OPTIONAL,
    base             XSD.String
}

ProcessReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProcessReasonType ::= SEQUENCE {
    languageID       XSD.Language OPTIONAL,
    languageLocaleID XSD.NormalizedString OPTIONAL,
    base             XSD.String
}

ProcurementProjectLotIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ProcurementSubTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProcurementTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProductTraceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ProfileExecutionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ProfileIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ProfileStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PromotionalEventTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ProviderTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PurposeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

PurposeType ::= SEQUENCE {
    languageID       XSD.Language OPTIONAL,
    languageLocaleID XSD.NormalizedString OPTIONAL,
    base             XSD.String
}

QualityControlCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

QuantityDiscrepancyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

QuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

RailCarIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RateType ::= SEQUENCE {
    format XSD.String OPTIONAL,
    base   XSD.Decimal
}

ReceivedDateType ::= SEQUENCE {
    base XSD.Date
}

ReceivedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ReceivedTenderQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ReferenceDateType ::= SEQUENCE {
    base XSD.Date
}

ReferenceEventCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ReferenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ReferenceTimeType ::= SEQUENCE {
    base XSD.Time
}

ReferenceType-1 ::= SEQUENCE {
    languageID       XSD.Language OPTIONAL,
    languageLocaleID XSD.NormalizedString OPTIONAL,
    base             XSD.String
}

ReferencedConsignmentIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RefrigeratedIndicatorType ::= SEQUENCE {
    base BOOLEAN
}

RefrigerationOnIndicatorType ::= SEQUENCE {
    base BOOLEAN
}

RegionType ::= SEQUENCE {
    languageID       XSD.Language OPTIONAL,
    languageLocaleID XSD.NormalizedString OPTIONAL,
    base             XSD.String
}

RegisteredDateType ::= SEQUENCE {
    base XSD.Date
}

RegisteredTimeType ::= SEQUENCE {
    base XSD.Time
}

RegistrationDateType ::= SEQUENCE {
    base XSD.Date
}

RegistrationExpirationDateType ::= SEQUENCE {
    base XSD.Date
}

RegistrationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RegistrationNameType ::= SEQUENCE {
    languageID       XSD.Language OPTIONAL,
    languageLocaleID XSD.NormalizedString OPTIONAL,
    base             XSD.String
}

RegistrationNationalityIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RegistrationNationalityType ::= SEQUENCE {
    languageID       XSD.Language OPTIONAL,
    languageLocaleID XSD.NormalizedString OPTIONAL,
    base             XSD.String
}

RejectActionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

RejectReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

RejectReasonType ::= SEQUENCE {
    languageID       XSD.Language OPTIONAL,
    languageLocaleID XSD.NormalizedString OPTIONAL,
    base             XSD.String
}

RejectedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

RejectionNoteType ::= SEQUENCE {
    languageID       XSD.Language OPTIONAL,
    languageLocaleID XSD.NormalizedString OPTIONAL,
    base             XSD.String
}

ReleaseIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ReliabilityPercentType ::= SEQUENCE {
    format XSD.String OPTIONAL,
    base   XSD.Decimal
}

RemarksType ::= SEQUENCE {
    languageID       XSD.Language OPTIONAL,
    languageLocaleID XSD.NormalizedString OPTIONAL,
    base             XSD.String
}

ReminderSequenceNumericType ::= SEQUENCE {
    format XSD.String OPTIONAL,
    base   XSD.Decimal
}

ReminderTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ReplenishmentOwnerDescriptionType ::= SEQUENCE {
    languageID       XSD.Language OPTIONAL,
    languageLocaleID XSD.NormalizedString OPTIONAL,
    base             XSD.String
}

RequestForQuotationLineIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RequestedDeliveryDateType ::= SEQUENCE {
    base XSD.Date
}

RequestedDespatchDateType ::= SEQUENCE {
    base XSD.Date
}

RequestedDespatchTimeType ::= SEQUENCE {
    base XSD.Time
}

RequestedInvoiceCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

RequestedPublicationDateType ::= SEQUENCE {
    base XSD.Date
}

RequiredCurriculaIndicatorType ::= SEQUENCE {
    base BOOLEAN
}

RequiredCustomsIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RequiredDeliveryDateType ::= SEQUENCE {
    base XSD.Date
}

RequiredDeliveryTimeType ::= SEQUENCE {
    base XSD.Time
}

RequiredFeeAmountType ::= SEQUENCE {
    currencyCodeListVersionID XSD.NormalizedString OPTIONAL,
    currencyID   XSD.NormalizedString OPTIONAL,
    base         XSD.Decimal
}

ResidenceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ResidenceTypeType ::= SEQUENCE {
    languageID       XSD.Language OPTIONAL,
    languageLocaleID XSD.NormalizedString OPTIONAL,
    base             XSD.String
}

ResidentOccupantsNumericType ::= SEQUENCE {
    format XSD.String OPTIONAL,
    base   XSD.Decimal
}

ResolutionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ResolutionDateType ::= SEQUENCE {
    base XSD.Date
}

ResolutionTimeType ::= SEQUENCE {
    base XSD.Time
}

ResolutionType ::= SEQUENCE {
    languageID       XSD.Language OPTIONAL,
    languageLocaleID XSD.NormalizedString OPTIONAL,
    base             XSD.String
}

ResponseCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ResponseDateType ::= SEQUENCE {
    base XSD.Date
}

ResponseTimeType ::= SEQUENCE {
    base XSD.Time
}

RetailEventNameType ::= SEQUENCE {
    languageID       XSD.Language OPTIONAL,
    languageLocaleID XSD.NormalizedString OPTIONAL,
    base             XSD.String
}

RetailEventStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ReturnabilityIndicatorType ::= SEQUENCE {
    base BOOLEAN
}

ReturnableMaterialIndicatorType ::= SEQUENCE {
    base BOOLEAN
}

ReturnableQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

RevisedForecastLineIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

RevisionDateType ::= SEQUENCE {
    base XSD.Date
}

RevisionStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

RevisionTimeType ::= SEQUENCE {
    base XSD.Time
}

RoamingPartnerNameType ::= SEQUENCE {
    languageID       XSD.Language OPTIONAL,
    languageLocaleID XSD.NormalizedString OPTIONAL,
    base             XSD.String
}

RoleCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

RoomType ::= SEQUENCE {
    languageID       XSD.Language OPTIONAL,
    languageLocaleID XSD.NormalizedString OPTIONAL,
    base             XSD.String
}

RoundingAmountType ::= SEQUENCE {
    currencyCodeListVersionID XSD.NormalizedString OPTIONAL,
    currencyID   XSD.NormalizedString OPTIONAL,
    base         XSD.Decimal
}

SalesOrderIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SalesOrderLineIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SchemeURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SealIssuerTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SealStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SealingPartyTypeType ::= SEQUENCE {
    languageID       XSD.Language OPTIONAL,
    languageLocaleID XSD.NormalizedString OPTIONAL,
    base             XSD.String
}

SecurityClassificationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SecurityIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SellerEventIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SequenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SequenceNumberIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SequenceNumericType ::= SEQUENCE {
    format XSD.String OPTIONAL,
    base   XSD.Decimal
}

SerialIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ServiceNameType ::= SEQUENCE {
    languageID       XSD.Language OPTIONAL,
    languageLocaleID XSD.NormalizedString OPTIONAL,
    base             XSD.String
}

ServiceNumberCalledType ::= SEQUENCE {
    languageID       XSD.Language OPTIONAL,
    languageLocaleID XSD.NormalizedString OPTIONAL,
    base             XSD.String
}

ServiceTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ServiceTypeType ::= SEQUENCE {
    languageID       XSD.Language OPTIONAL,
    languageLocaleID XSD.NormalizedString OPTIONAL,
    base             XSD.String
}

SettlementDiscountAmountType ::= SEQUENCE {
    currencyCodeListVersionID XSD.NormalizedString OPTIONAL,
    currencyID   XSD.NormalizedString OPTIONAL,
    base         XSD.Decimal
}

SettlementDiscountPercentType ::= SEQUENCE {
    format XSD.String OPTIONAL,
    base   XSD.Decimal
}

SharesNumberQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ShippingMarksType ::= SEQUENCE {
    languageID       XSD.Language OPTIONAL,
    languageLocaleID XSD.NormalizedString OPTIONAL,
    base             XSD.String
}

ShippingOrderIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ShippingPriorityLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ShortQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ShortageActionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SignatureIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SignatureMethodType-1 ::= SEQUENCE {
    languageID       XSD.Language OPTIONAL,
    languageLocaleID XSD.NormalizedString OPTIONAL,
    base             XSD.String
}

SizeTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SoleProprietorshipIndicatorType ::= SEQUENCE {
    base BOOLEAN
}

SourceCurrencyBaseRateType ::= SEQUENCE {
    format XSD.String OPTIONAL,
    base   XSD.Decimal
}

SourceCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SourceForecastIssueDateType ::= SEQUENCE {
    base XSD.Date
}

SourceForecastIssueTimeType ::= SEQUENCE {
    base XSD.Time
}

SourceValueMeasureType ::= SEQUENCE {
    unitCode     XSD.NormalizedString OPTIONAL,
    unitCodeListVersionID XSD.NormalizedString OPTIONAL,
    base         XSD.Decimal
}

SpecialInstructionsType ::= SEQUENCE {
    languageID       XSD.Language OPTIONAL,
    languageLocaleID XSD.NormalizedString OPTIONAL,
    base             XSD.String
}

SpecialSecurityIndicatorType ::= SEQUENCE {
    base BOOLEAN
}

SpecialServiceInstructionsType ::= SEQUENCE {
    languageID       XSD.Language OPTIONAL,
    languageLocaleID XSD.NormalizedString OPTIONAL,
    base             XSD.String
}

SpecialTermsType ::= SEQUENCE {
    languageID       XSD.Language OPTIONAL,
    languageLocaleID XSD.NormalizedString OPTIONAL,
    base             XSD.String
}

SpecialTransportRequirmentsType ::= SEQUENCE {
    languageID       XSD.Language OPTIONAL,
    languageLocaleID XSD.NormalizedString OPTIONAL,
    base             XSD.String
}

SpecificationIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SpecificationTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SplitConsignmentIndicatorType ::= SEQUENCE {
    base BOOLEAN
}

StartDateType ::= SEQUENCE {
    base XSD.Date
}

StartTimeType ::= SEQUENCE {
    base XSD.Time
}

StatementTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

StatusAvailableIndicatorType ::= SEQUENCE {
    base BOOLEAN
}

StatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

StatusReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

StatusReasonType ::= SEQUENCE {
    languageID       XSD.Language OPTIONAL,
    languageLocaleID XSD.NormalizedString OPTIONAL,
    base             XSD.String
}

StreetNameType ::= SEQUENCE {
    languageID       XSD.Language OPTIONAL,
    languageLocaleID XSD.NormalizedString OPTIONAL,
    base             XSD.String
}

SubmissionDateType ::= SEQUENCE {
    base XSD.Date
}

SubmissionDueDateType ::= SEQUENCE {
    base XSD.Date
}

SubmissionMethodCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SubscriberIDType-1 ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SubscriberIDTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SubscriberIDTypeType ::= SEQUENCE {
    languageID       XSD.Language OPTIONAL,
    languageLocaleID XSD.NormalizedString OPTIONAL,
    base             XSD.String
}

SubscriberTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SubscriberTypeIdentifierType ::= SEQUENCE {
    languageID       XSD.Language OPTIONAL,
    languageLocaleID XSD.NormalizedString OPTIONAL,
    base             XSD.String
}

SubstitutionStatusCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

SuccessiveSequenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SummaryDescriptionType ::= SEQUENCE {
    languageID       XSD.Language OPTIONAL,
    languageLocaleID XSD.NormalizedString OPTIONAL,
    base             XSD.String
}

SupplierAssignedAccountIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

SupplyChainActivityTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TareWeightMeasureType ::= SEQUENCE {
    unitCode     XSD.NormalizedString OPTIONAL,
    unitCodeListVersionID XSD.NormalizedString OPTIONAL,
    base         XSD.Decimal
}

TargetCurrencyBaseRateType ::= SEQUENCE {
    format XSD.String OPTIONAL,
    base   XSD.Decimal
}

TargetCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TargetInventoryQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TargetServicePercentType ::= SEQUENCE {
    format XSD.String OPTIONAL,
    base   XSD.Decimal
}

TariffClassCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TariffCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TariffDescriptionType ::= SEQUENCE {
    languageID       XSD.Language OPTIONAL,
    languageLocaleID XSD.NormalizedString OPTIONAL,
    base             XSD.String
}

TaxAmountType ::= SEQUENCE {
    currencyCodeListVersionID XSD.NormalizedString OPTIONAL,
    currencyID   XSD.NormalizedString OPTIONAL,
    base         XSD.Decimal
}

TaxCurrencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TaxEnergyAmountType ::= SEQUENCE {
    currencyCodeListVersionID XSD.NormalizedString OPTIONAL,
    currencyID   XSD.NormalizedString OPTIONAL,
    base         XSD.Decimal
}

TaxEnergyBalanceAmountType ::= SEQUENCE {
    currencyCodeListVersionID XSD.NormalizedString OPTIONAL,
    currencyID   XSD.NormalizedString OPTIONAL,
    base         XSD.Decimal
}

TaxEnergyOnAccountAmountType ::= SEQUENCE {
    currencyCodeListVersionID XSD.NormalizedString OPTIONAL,
    currencyID   XSD.NormalizedString OPTIONAL,
    base         XSD.Decimal
}

TaxEvidenceIndicatorType ::= SEQUENCE {
    base BOOLEAN
}

TaxExclusiveAmountType ::= SEQUENCE {
    currencyCodeListVersionID XSD.NormalizedString OPTIONAL,
    currencyID   XSD.NormalizedString OPTIONAL,
    base         XSD.Decimal
}

TaxExemptionReasonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TaxExemptionReasonType ::= SEQUENCE {
    languageID       XSD.Language OPTIONAL,
    languageLocaleID XSD.NormalizedString OPTIONAL,
    base             XSD.String
}

TaxIncludedIndicatorType ::= SEQUENCE {
    base BOOLEAN
}

TaxInclusiveAmountType ::= SEQUENCE {
    currencyCodeListVersionID XSD.NormalizedString OPTIONAL,
    currencyID   XSD.NormalizedString OPTIONAL,
    base         XSD.Decimal
}

TaxLevelCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TaxPointDateType ::= SEQUENCE {
    base XSD.Date
}

TaxTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TaxableAmountType ::= SEQUENCE {
    currencyCodeListVersionID XSD.NormalizedString OPTIONAL,
    currencyID   XSD.NormalizedString OPTIONAL,
    base         XSD.Decimal
}

TechnicalCommitteeDescriptionType ::= SEQUENCE {
    languageID       XSD.Language OPTIONAL,
    languageLocaleID XSD.NormalizedString OPTIONAL,
    base             XSD.String
}

TechnicalNameType ::= SEQUENCE {
    languageID       XSD.Language OPTIONAL,
    languageLocaleID XSD.NormalizedString OPTIONAL,
    base             XSD.String
}

TelecommunicationsServiceCallCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TelecommunicationsServiceCallType ::= SEQUENCE {
    languageID       XSD.Language OPTIONAL,
    languageLocaleID XSD.NormalizedString OPTIONAL,
    base             XSD.String
}

TelecommunicationsServiceCategoryCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TelecommunicationsServiceCategoryType ::= SEQUENCE {
    languageID       XSD.Language OPTIONAL,
    languageLocaleID XSD.NormalizedString OPTIONAL,
    base             XSD.String
}

TelecommunicationsSupplyTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TelecommunicationsSupplyTypeType ::= SEQUENCE {
    languageID       XSD.Language OPTIONAL,
    languageLocaleID XSD.NormalizedString OPTIONAL,
    base             XSD.String
}

TelefaxType ::= SEQUENCE {
    languageID       XSD.Language OPTIONAL,
    languageLocaleID XSD.NormalizedString OPTIONAL,
    base             XSD.String
}

TelephoneType ::= SEQUENCE {
    languageID       XSD.Language OPTIONAL,
    languageLocaleID XSD.NormalizedString OPTIONAL,
    base             XSD.String
}

TenderEnvelopeIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TenderEnvelopeTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TenderResultCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TenderTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TendererRequirementTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TestMethodType ::= SEQUENCE {
    languageID       XSD.Language OPTIONAL,
    languageLocaleID XSD.NormalizedString OPTIONAL,
    base             XSD.String
}

TextType ::= SEQUENCE {
    languageID       XSD.Language OPTIONAL,
    languageLocaleID XSD.NormalizedString OPTIONAL,
    base             XSD.String
}

ThirdPartyPayerIndicatorType ::= SEQUENCE {
    base BOOLEAN
}

ThresholdAmountType ::= SEQUENCE {
    currencyCodeListVersionID XSD.NormalizedString OPTIONAL,
    currencyID   XSD.NormalizedString OPTIONAL,
    base         XSD.Decimal
}

ThresholdQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ThresholdValueComparisonCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TierRangeType ::= SEQUENCE {
    languageID       XSD.Language OPTIONAL,
    languageLocaleID XSD.NormalizedString OPTIONAL,
    base             XSD.String
}

TierRatePercentType ::= SEQUENCE {
    format XSD.String OPTIONAL,
    base   XSD.Decimal
}

TimeAmountType ::= SEQUENCE {
    languageID       XSD.Language OPTIONAL,
    languageLocaleID XSD.NormalizedString OPTIONAL,
    base             XSD.String
}

TimeDeltaDaysQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TimeDeviationIndicatorType ::= SEQUENCE {
    base BOOLEAN
}

TimeFrequencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TimezoneOffsetType ::= SEQUENCE {
    languageID       XSD.Language OPTIONAL,
    languageLocaleID XSD.NormalizedString OPTIONAL,
    base             XSD.String
}

TimingComplaintCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TimingComplaintType ::= SEQUENCE {
    languageID       XSD.Language OPTIONAL,
    languageLocaleID XSD.NormalizedString OPTIONAL,
    base             XSD.String
}

TitleType ::= SEQUENCE {
    languageID       XSD.Language OPTIONAL,
    languageLocaleID XSD.NormalizedString OPTIONAL,
    base             XSD.String
}

ToOrderIndicatorType ::= SEQUENCE {
    base BOOLEAN
}

TotalAmountType ::= SEQUENCE {
    currencyCodeListVersionID XSD.NormalizedString OPTIONAL,
    currencyID   XSD.NormalizedString OPTIONAL,
    base         XSD.Decimal
}

TotalBalanceAmountType ::= SEQUENCE {
    currencyCodeListVersionID XSD.NormalizedString OPTIONAL,
    currencyID   XSD.NormalizedString OPTIONAL,
    base         XSD.Decimal
}

TotalConsumedQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalCreditAmountType ::= SEQUENCE {
    currencyCodeListVersionID XSD.NormalizedString OPTIONAL,
    currencyID   XSD.NormalizedString OPTIONAL,
    base         XSD.Decimal
}

TotalDebitAmountType ::= SEQUENCE {
    currencyCodeListVersionID XSD.NormalizedString OPTIONAL,
    currencyID   XSD.NormalizedString OPTIONAL,
    base         XSD.Decimal
}

TotalDeliveredQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalGoodsItemQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalInvoiceAmountType ::= SEQUENCE {
    currencyCodeListVersionID XSD.NormalizedString OPTIONAL,
    currencyID   XSD.NormalizedString OPTIONAL,
    base         XSD.Decimal
}

TotalMeteredQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalPackageQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalPackagesQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TotalPaymentAmountType ::= SEQUENCE {
    currencyCodeListVersionID XSD.NormalizedString OPTIONAL,
    currencyID   XSD.NormalizedString OPTIONAL,
    base         XSD.Decimal
}

TotalTaskAmountType ::= SEQUENCE {
    currencyCodeListVersionID XSD.NormalizedString OPTIONAL,
    currencyID   XSD.NormalizedString OPTIONAL,
    base         XSD.Decimal
}

TotalTaxAmountType ::= SEQUENCE {
    currencyCodeListVersionID XSD.NormalizedString OPTIONAL,
    currencyID   XSD.NormalizedString OPTIONAL,
    base         XSD.Decimal
}

TotalTransportHandlingUnitQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TraceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TrackingDeviceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TrackingIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TradeItemPackingLabelingTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TradeServiceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TradingRestrictionsType ::= SEQUENCE {
    languageID       XSD.Language OPTIONAL,
    languageLocaleID XSD.NormalizedString OPTIONAL,
    base             XSD.String
}

TrainIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TransactionCurrencyTaxAmountType ::= SEQUENCE {
    currencyCodeListVersionID XSD.NormalizedString OPTIONAL,
    currencyID   XSD.NormalizedString OPTIONAL,
    base         XSD.Decimal
}

TransitDirectionCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportAuthorizationCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportEmergencyCardCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportEquipmentTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportEventTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportExecutionPlanReferenceIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TransportHandlingUnitTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportMeansTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportModeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportServiceCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

TransportServiceProviderCancellationIndicatorType ::= SEQUENCE {
    base BOOLEAN
}

TransportServiceProviderCompletionIndicatorType ::= SEQUENCE {
    base BOOLEAN
}

TransportServiceProviderReadyForExecutionIndicatorType ::= SEQUENCE {
    base BOOLEAN
}

TransportServiceProviderRemarksType ::= SEQUENCE {
    languageID       XSD.Language OPTIONAL,
    languageLocaleID XSD.NormalizedString OPTIONAL,
    base             XSD.String
}

TransportServiceProviderSpecialTermsType ::= SEQUENCE {
    languageID       XSD.Language OPTIONAL,
    languageLocaleID XSD.NormalizedString OPTIONAL,
    base             XSD.String
}

TransportUserCancellationIndicatorType ::= SEQUENCE {
    base BOOLEAN
}

TransportUserCompletionIndicatorType ::= SEQUENCE {
    base BOOLEAN
}

TransportUserReadyForExecutionIndicatorType ::= SEQUENCE {
    base BOOLEAN
}

TransportUserRemarksType ::= SEQUENCE {
    languageID       XSD.Language OPTIONAL,
    languageLocaleID XSD.NormalizedString OPTIONAL,
    base             XSD.String
}

TransportUserSpecialTermsType ::= SEQUENCE {
    languageID       XSD.Language OPTIONAL,
    languageLocaleID XSD.NormalizedString OPTIONAL,
    base             XSD.String
}

TransportationServiceDescriptionType ::= SEQUENCE {
    languageID       XSD.Language OPTIONAL,
    languageLocaleID XSD.NormalizedString OPTIONAL,
    base             XSD.String
}

TransportationServiceDetailsURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

TypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

UBLVersionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

UNDGCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

URIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

UUIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

UnknownPriceIndicatorType ::= SEQUENCE {
    base BOOLEAN
}

UpperOrangeHazardPlacardIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

UrgencyCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

UtilityStatementTypeCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ValidateProcessType ::= SEQUENCE {
    languageID       XSD.Language OPTIONAL,
    languageLocaleID XSD.NormalizedString OPTIONAL,
    base             XSD.String
}

ValidateToolType ::= SEQUENCE {
    languageID       XSD.Language OPTIONAL,
    languageLocaleID XSD.NormalizedString OPTIONAL,
    base             XSD.String
}

ValidateToolVersionType ::= SEQUENCE {
    languageID       XSD.Language OPTIONAL,
    languageLocaleID XSD.NormalizedString OPTIONAL,
    base             XSD.String
}

ValidationDateType ::= SEQUENCE {
    base XSD.Date
}

ValidationResultCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

ValidationTimeType ::= SEQUENCE {
    base XSD.Time
}

ValidatorIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

ValidityStartDateType ::= SEQUENCE {
    base XSD.Date
}

ValueAmountType ::= SEQUENCE {
    currencyCodeListVersionID XSD.NormalizedString OPTIONAL,
    currencyID   XSD.NormalizedString OPTIONAL,
    base         XSD.Decimal
}

ValueMeasureType ::= SEQUENCE {
    unitCode     XSD.NormalizedString OPTIONAL,
    unitCodeListVersionID XSD.NormalizedString OPTIONAL,
    base         XSD.Decimal
}

ValueQualifierType ::= SEQUENCE {
    languageID       XSD.Language OPTIONAL,
    languageLocaleID XSD.NormalizedString OPTIONAL,
    base             XSD.String
}

ValueQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

ValueType ::= SEQUENCE {
    languageID       XSD.Language OPTIONAL,
    languageLocaleID XSD.NormalizedString OPTIONAL,
    base             XSD.String
}

VarianceQuantityType ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

VariantConstraintIndicatorType ::= SEQUENCE {
    base BOOLEAN
}

VariantIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

VersionIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

VesselIDType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

VesselNameType ::= SEQUENCE {
    languageID       XSD.Language OPTIONAL,
    languageLocaleID XSD.NormalizedString OPTIONAL,
    base             XSD.String
}

WarrantyInformationType ::= SEQUENCE {
    languageID       XSD.Language OPTIONAL,
    languageLocaleID XSD.NormalizedString OPTIONAL,
    base             XSD.String
}

WebsiteURIType ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

WeightNumericType ::= SEQUENCE {
    format XSD.String OPTIONAL,
    base   XSD.Decimal
}

WeightType ::= SEQUENCE {
    languageID       XSD.Language OPTIONAL,
    languageLocaleID XSD.NormalizedString OPTIONAL,
    base             XSD.String
}

WeightingAlgorithmCodeType ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

XPathType ::= SEQUENCE {
    languageID       XSD.Language OPTIONAL,
    languageLocaleID XSD.NormalizedString OPTIONAL,
    base             XSD.String
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:CommonBasicComponents-2"
	PREFIX "cbc"
    NOT NAMESPACE AcceptedVariantsDescriptionType.languageID, 
	AcceptedVariantsDescriptionType.languageLocaleID, 
	AccountFormatCodeType.languageID, AccountFormatCodeType.listAgencyID, 
	AccountFormatCodeType.listAgencyName, AccountFormatCodeType.listID, 
	AccountFormatCodeType.listName, AccountFormatCodeType.listSchemeURI, 
	AccountFormatCodeType.listURI, AccountFormatCodeType.listVersionID, 
	AccountFormatCodeType.name, AccountIDType.schemeAgencyID, 
	AccountIDType.schemeAgencyName, AccountIDType.schemeDataURI, 
	AccountIDType.schemeID, AccountIDType.schemeName, 
	AccountIDType.schemeURI, AccountIDType.schemeVersionID, 
	AccountTypeCodeType.languageID, AccountTypeCodeType.listAgencyID, 
	AccountTypeCodeType.listAgencyName, AccountTypeCodeType.listID, 
	AccountTypeCodeType.listName, AccountTypeCodeType.listSchemeURI, 
	AccountTypeCodeType.listURI, AccountTypeCodeType.listVersionID, 
	AccountTypeCodeType.name, AccountingCostCodeType.languageID, 
	AccountingCostCodeType.listAgencyID, 
	AccountingCostCodeType.listAgencyName, AccountingCostCodeType.listID, 
	AccountingCostCodeType.listName, AccountingCostCodeType.listSchemeURI,
	AccountingCostCodeType.listURI, AccountingCostCodeType.listVersionID, 
	AccountingCostCodeType.name, AccountingCostType.languageID, 
	AccountingCostType.languageLocaleID, ActionCodeType.languageID, 
	ActionCodeType.listAgencyID, ActionCodeType.listAgencyName, 
	ActionCodeType.listID, ActionCodeType.listName, 
	ActionCodeType.listSchemeURI, ActionCodeType.listURI, 
	ActionCodeType.listVersionID, ActionCodeType.name, 
	ActivityCodeType.languageID, ActivityCodeType.listAgencyID, 
	ActivityCodeType.listAgencyName, ActivityCodeType.listID, 
	ActivityCodeType.listName, ActivityCodeType.listSchemeURI, 
	ActivityCodeType.listURI, ActivityCodeType.listVersionID, 
	ActivityCodeType.name, 
	ActualTemperatureReductionQuantityType.unitCode, 
	ActualTemperatureReductionQuantityType.unitCodeListAgencyID, 
	ActualTemperatureReductionQuantityType.unitCodeListAgencyName, 
	ActualTemperatureReductionQuantityType.unitCodeListID, 
	AdditionalAccountIDType.schemeAgencyID, 
	AdditionalAccountIDType.schemeAgencyName, 
	AdditionalAccountIDType.schemeDataURI, 
	AdditionalAccountIDType.schemeID, AdditionalAccountIDType.schemeName, 
	AdditionalAccountIDType.schemeURI, 
	AdditionalAccountIDType.schemeVersionID, 
	AdditionalInformationType.languageID, 
	AdditionalInformationType.languageLocaleID, 
	AdditionalStreetNameType.languageID, 
	AdditionalStreetNameType.languageLocaleID, 
	AddressFormatCodeType.languageID, AddressFormatCodeType.listAgencyID, 
	AddressFormatCodeType.listAgencyName, AddressFormatCodeType.listID, 
	AddressFormatCodeType.listName, AddressFormatCodeType.listSchemeURI, 
	AddressFormatCodeType.listURI, AddressFormatCodeType.listVersionID, 
	AddressFormatCodeType.name, AddressTypeCodeType.languageID, 
	AddressTypeCodeType.listAgencyID, AddressTypeCodeType.listAgencyName, 
	AddressTypeCodeType.listID, AddressTypeCodeType.listName, 
	AddressTypeCodeType.listSchemeURI, AddressTypeCodeType.listURI, 
	AddressTypeCodeType.listVersionID, AddressTypeCodeType.name, 
	AdjustmentReasonCodeType.languageID, 
	AdjustmentReasonCodeType.listAgencyID, 
	AdjustmentReasonCodeType.listAgencyName, 
	AdjustmentReasonCodeType.listID, AdjustmentReasonCodeType.listName, 
	AdjustmentReasonCodeType.listSchemeURI, 
	AdjustmentReasonCodeType.listURI, 
	AdjustmentReasonCodeType.listVersionID, AdjustmentReasonCodeType.name,
	AdmissionCodeType.languageID, AdmissionCodeType.listAgencyID, 
	AdmissionCodeType.listAgencyName, AdmissionCodeType.listID, 
	AdmissionCodeType.listName, AdmissionCodeType.listSchemeURI, 
	AdmissionCodeType.listURI, AdmissionCodeType.listVersionID, 
	AdmissionCodeType.name, 
	AdvertisementAmountType.currencyCodeListVersionID, 
	AdvertisementAmountType.currencyID, AgencyIDType.schemeAgencyID, 
	AgencyIDType.schemeAgencyName, AgencyIDType.schemeDataURI, 
	AgencyIDType.schemeID, AgencyIDType.schemeName, 
	AgencyIDType.schemeURI, AgencyIDType.schemeVersionID, 
	AgencyNameType.languageID, AgencyNameType.languageLocaleID, 
	AirFlowPercentType.format, AircraftIDType.schemeAgencyID, 
	AircraftIDType.schemeAgencyName, AircraftIDType.schemeDataURI, 
	AircraftIDType.schemeID, AircraftIDType.schemeName, 
	AircraftIDType.schemeURI, AircraftIDType.schemeVersionID, 
	AliasNameType.languageID, AliasNameType.languageLocaleID, 
	AllowanceChargeReasonCodeType.languageID, 
	AllowanceChargeReasonCodeType.listAgencyID, 
	AllowanceChargeReasonCodeType.listAgencyName, 
	AllowanceChargeReasonCodeType.listID, 
	AllowanceChargeReasonCodeType.listName, 
	AllowanceChargeReasonCodeType.listSchemeURI, 
	AllowanceChargeReasonCodeType.listURI, 
	AllowanceChargeReasonCodeType.listVersionID, 
	AllowanceChargeReasonCodeType.name, 
	AllowanceChargeReasonType.languageID, 
	AllowanceChargeReasonType.languageLocaleID, 
	AllowanceTotalAmountType.currencyCodeListVersionID, 
	AllowanceTotalAmountType.currencyID, AltitudeMeasureType.unitCode, 
	AltitudeMeasureType.unitCodeListVersionID, AmountRateType.format, 
	AmountType.currencyCodeListVersionID, AmountType.currencyID, 
	AnnualAverageAmountType.currencyCodeListVersionID, 
	AnnualAverageAmountType.currencyID, 
	ApplicationStatusCodeType.languageID, 
	ApplicationStatusCodeType.listAgencyID, 
	ApplicationStatusCodeType.listAgencyName, 
	ApplicationStatusCodeType.listID, ApplicationStatusCodeType.listName, 
	ApplicationStatusCodeType.listSchemeURI, 
	ApplicationStatusCodeType.listURI, 
	ApplicationStatusCodeType.listVersionID, 
	ApplicationStatusCodeType.name, ApprovalStatusType.languageID, 
	ApprovalStatusType.languageLocaleID, AttributeIDType.schemeAgencyID, 
	AttributeIDType.schemeAgencyName, AttributeIDType.schemeDataURI, 
	AttributeIDType.schemeID, AttributeIDType.schemeName, 
	AttributeIDType.schemeURI, AttributeIDType.schemeVersionID, 
	AuctionURIType.schemeAgencyID, AuctionURIType.schemeAgencyName, 
	AuctionURIType.schemeDataURI, AuctionURIType.schemeID, 
	AuctionURIType.schemeName, AuctionURIType.schemeURI, 
	AuctionURIType.schemeVersionID, AvailabilityStatusCodeType.languageID,
	AvailabilityStatusCodeType.listAgencyID, 
	AvailabilityStatusCodeType.listAgencyName, 
	AvailabilityStatusCodeType.listID, 
	AvailabilityStatusCodeType.listName, 
	AvailabilityStatusCodeType.listSchemeURI, 
	AvailabilityStatusCodeType.listURI, 
	AvailabilityStatusCodeType.listVersionID, 
	AvailabilityStatusCodeType.name, 
	AverageAmountType.currencyCodeListVersionID, 
	AverageAmountType.currencyID, 
	AverageSubsequentContractAmountType.currencyCodeListVersionID, 
	AverageSubsequentContractAmountType.currencyID, 
	AwardingCriteriaDescriptionType.languageID, 
	AwardingCriteriaDescriptionType.languageLocaleID, 
	AwardingCriteriaIDType.schemeAgencyID, 
	AwardingCriteriaIDType.schemeAgencyName, 
	AwardingCriteriaIDType.schemeDataURI, AwardingCriteriaIDType.schemeID,
	AwardingCriteriaIDType.schemeName, AwardingCriteriaIDType.schemeURI, 
	AwardingCriteriaIDType.schemeVersionID, 
	AwardingCriteriaTypeCodeType.languageID, 
	AwardingCriteriaTypeCodeType.listAgencyID, 
	AwardingCriteriaTypeCodeType.listAgencyName, 
	AwardingCriteriaTypeCodeType.listID, 
	AwardingCriteriaTypeCodeType.listName, 
	AwardingCriteriaTypeCodeType.listSchemeURI, 
	AwardingCriteriaTypeCodeType.listURI, 
	AwardingCriteriaTypeCodeType.listVersionID, 
	AwardingCriteriaTypeCodeType.name, 
	AwardingMethodTypeCodeType.languageID, 
	AwardingMethodTypeCodeType.listAgencyID, 
	AwardingMethodTypeCodeType.listAgencyName, 
	AwardingMethodTypeCodeType.listID, 
	AwardingMethodTypeCodeType.listName, 
	AwardingMethodTypeCodeType.listSchemeURI, 
	AwardingMethodTypeCodeType.listURI, 
	AwardingMethodTypeCodeType.listVersionID, 
	AwardingMethodTypeCodeType.name, BackorderQuantityType.unitCode, 
	BackorderQuantityType.unitCodeListAgencyID, 
	BackorderQuantityType.unitCodeListAgencyName, 
	BackorderQuantityType.unitCodeListID, BackorderReasonType.languageID, 
	BackorderReasonType.languageLocaleID, 
	BalanceAmountType.currencyCodeListVersionID, 
	BalanceAmountType.currencyID, 
	BaseAmountType.currencyCodeListVersionID, BaseAmountType.currencyID, 
	BaseQuantityType.unitCode, BaseQuantityType.unitCodeListAgencyID, 
	BaseQuantityType.unitCodeListAgencyName, 
	BaseQuantityType.unitCodeListID, BaseUnitMeasureType.unitCode, 
	BaseUnitMeasureType.unitCodeListVersionID, 
	BasicConsumedQuantityType.unitCode, 
	BasicConsumedQuantityType.unitCodeListAgencyID, 
	BasicConsumedQuantityType.unitCodeListAgencyName, 
	BasicConsumedQuantityType.unitCodeListID, BatchQuantityType.unitCode, 
	BatchQuantityType.unitCodeListAgencyID, 
	BatchQuantityType.unitCodeListAgencyName, 
	BatchQuantityType.unitCodeListID, BlockNameType.languageID, 
	BlockNameType.languageLocaleID, BrandNameType.languageID, 
	BrandNameType.languageLocaleID, BrokerAssignedIDType.schemeAgencyID, 
	BrokerAssignedIDType.schemeAgencyName, 
	BrokerAssignedIDType.schemeDataURI, BrokerAssignedIDType.schemeID, 
	BrokerAssignedIDType.schemeName, BrokerAssignedIDType.schemeURI, 
	BrokerAssignedIDType.schemeVersionID, BudgetYearNumericType.format, 
	BuildingNameType.languageID, BuildingNameType.languageLocaleID, 
	BuildingNumberType.languageID, BuildingNumberType.languageLocaleID, 
	BusinessClassificationEvidenceIDType.schemeAgencyID, 
	BusinessClassificationEvidenceIDType.schemeAgencyName, 
	BusinessClassificationEvidenceIDType.schemeDataURI, 
	BusinessClassificationEvidenceIDType.schemeID, 
	BusinessClassificationEvidenceIDType.schemeName, 
	BusinessClassificationEvidenceIDType.schemeURI, 
	BusinessClassificationEvidenceIDType.schemeVersionID, 
	BusinessIdentityEvidenceIDType.schemeAgencyID, 
	BusinessIdentityEvidenceIDType.schemeAgencyName, 
	BusinessIdentityEvidenceIDType.schemeDataURI, 
	BusinessIdentityEvidenceIDType.schemeID, 
	BusinessIdentityEvidenceIDType.schemeName, 
	BusinessIdentityEvidenceIDType.schemeURI, 
	BusinessIdentityEvidenceIDType.schemeVersionID, 
	BuyerEventIDType.schemeAgencyID, BuyerEventIDType.schemeAgencyName, 
	BuyerEventIDType.schemeDataURI, BuyerEventIDType.schemeID, 
	BuyerEventIDType.schemeName, BuyerEventIDType.schemeURI, 
	BuyerEventIDType.schemeVersionID, BuyerProfileURIType.schemeAgencyID, 
	BuyerProfileURIType.schemeAgencyName, 
	BuyerProfileURIType.schemeDataURI, BuyerProfileURIType.schemeID, 
	BuyerProfileURIType.schemeName, BuyerProfileURIType.schemeURI, 
	BuyerProfileURIType.schemeVersionID, CV2IDType.schemeAgencyID, 
	CV2IDType.schemeAgencyName, CV2IDType.schemeDataURI, 
	CV2IDType.schemeID, CV2IDType.schemeName, CV2IDType.schemeURI, 
	CV2IDType.schemeVersionID, CalculationExpressionCodeType.languageID, 
	CalculationExpressionCodeType.listAgencyID, 
	CalculationExpressionCodeType.listAgencyName, 
	CalculationExpressionCodeType.listID, 
	CalculationExpressionCodeType.listName, 
	CalculationExpressionCodeType.listSchemeURI, 
	CalculationExpressionCodeType.listURI, 
	CalculationExpressionCodeType.listVersionID, 
	CalculationExpressionCodeType.name, 
	CalculationExpressionType.languageID, 
	CalculationExpressionType.languageLocaleID, 
	CalculationRateType.format, CalculationSequenceNumericType.format, 
	CallBaseAmountType.currencyCodeListVersionID, 
	CallBaseAmountType.currencyID, 
	CallExtensionAmountType.currencyCodeListVersionID, 
	CallExtensionAmountType.currencyID, CancellationNoteType.languageID, 
	CancellationNoteType.languageLocaleID, 
	CanonicalizationMethodType-1.languageID, 
	CanonicalizationMethodType-1.languageLocaleID, 
	CapabilityTypeCodeType.languageID, 
	CapabilityTypeCodeType.listAgencyID, 
	CapabilityTypeCodeType.listAgencyName, CapabilityTypeCodeType.listID, 
	CapabilityTypeCodeType.listName, CapabilityTypeCodeType.listSchemeURI,
	CapabilityTypeCodeType.listURI, CapabilityTypeCodeType.listVersionID, 
	CapabilityTypeCodeType.name, CardChipCodeType.languageID, 
	CardChipCodeType.listAgencyID, CardChipCodeType.listAgencyName, 
	CardChipCodeType.listID, CardChipCodeType.listName, 
	CardChipCodeType.listSchemeURI, CardChipCodeType.listURI, 
	CardChipCodeType.listVersionID, CardChipCodeType.name, 
	CardTypeCodeType.languageID, CardTypeCodeType.listAgencyID, 
	CardTypeCodeType.listAgencyName, CardTypeCodeType.listID, 
	CardTypeCodeType.listName, CardTypeCodeType.listSchemeURI, 
	CardTypeCodeType.listURI, CardTypeCodeType.listVersionID, 
	CardTypeCodeType.name, CargoTypeCodeType.languageID, 
	CargoTypeCodeType.listAgencyID, CargoTypeCodeType.listAgencyName, 
	CargoTypeCodeType.listID, CargoTypeCodeType.listName, 
	CargoTypeCodeType.listSchemeURI, CargoTypeCodeType.listURI, 
	CargoTypeCodeType.listVersionID, CargoTypeCodeType.name, 
	CarrierAssignedIDType.schemeAgencyID, 
	CarrierAssignedIDType.schemeAgencyName, 
	CarrierAssignedIDType.schemeDataURI, CarrierAssignedIDType.schemeID, 
	CarrierAssignedIDType.schemeName, CarrierAssignedIDType.schemeURI, 
	CarrierAssignedIDType.schemeVersionID, 
	CarrierServiceInstructionsType.languageID, 
	CarrierServiceInstructionsType.languageLocaleID, 
	CategoryNameType.languageID, CategoryNameType.languageLocaleID, 
	CertificateTypeCodeType.languageID, 
	CertificateTypeCodeType.listAgencyID, 
	CertificateTypeCodeType.listAgencyName, 
	CertificateTypeCodeType.listID, CertificateTypeCodeType.listName, 
	CertificateTypeCodeType.listSchemeURI, 
	CertificateTypeCodeType.listURI, 
	CertificateTypeCodeType.listVersionID, CertificateTypeCodeType.name, 
	CertificateTypeType.languageID, CertificateTypeType.languageLocaleID, 
	ChangeConditionsType.languageID, 
	ChangeConditionsType.languageLocaleID, ChannelCodeType.languageID, 
	ChannelCodeType.listAgencyID, ChannelCodeType.listAgencyName, 
	ChannelCodeType.listID, ChannelCodeType.listName, 
	ChannelCodeType.listSchemeURI, ChannelCodeType.listURI, 
	ChannelCodeType.listVersionID, ChannelCodeType.name, 
	ChannelType.languageID, ChannelType.languageLocaleID, 
	CharacterSetCodeType.languageID, CharacterSetCodeType.listAgencyID, 
	CharacterSetCodeType.listAgencyName, CharacterSetCodeType.listID, 
	CharacterSetCodeType.listName, CharacterSetCodeType.listSchemeURI, 
	CharacterSetCodeType.listURI, CharacterSetCodeType.listVersionID, 
	CharacterSetCodeType.name, CharacteristicsType.languageID, 
	CharacteristicsType.languageLocaleID, 
	ChargeTotalAmountType.currencyCodeListVersionID, 
	ChargeTotalAmountType.currencyID, ChargeableQuantityType.unitCode, 
	ChargeableQuantityType.unitCodeListAgencyID, 
	ChargeableQuantityType.unitCodeListAgencyName, 
	ChargeableQuantityType.unitCodeListID, 
	ChargeableWeightMeasureType.unitCode, 
	ChargeableWeightMeasureType.unitCodeListVersionID, 
	ChipApplicationIDType.schemeAgencyID, 
	ChipApplicationIDType.schemeAgencyName, 
	ChipApplicationIDType.schemeDataURI, ChipApplicationIDType.schemeID, 
	ChipApplicationIDType.schemeName, ChipApplicationIDType.schemeURI, 
	ChipApplicationIDType.schemeVersionID, CityNameType.languageID, 
	CityNameType.languageLocaleID, CitySubdivisionNameType.languageID, 
	CitySubdivisionNameType.languageLocaleID, ClauseCodeType.languageID, 
	ClauseCodeType.listAgencyID, ClauseCodeType.listAgencyName, 
	ClauseCodeType.listID, ClauseCodeType.listName, 
	ClauseCodeType.listSchemeURI, ClauseCodeType.listURI, 
	ClauseCodeType.listVersionID, ClauseCodeType.name, 
	ClauseType.languageID, ClauseType.languageLocaleID, 
	CodeValueType.languageID, CodeValueType.languageLocaleID, 
	CollaborationPriorityCodeType.languageID, 
	CollaborationPriorityCodeType.listAgencyID, 
	CollaborationPriorityCodeType.listAgencyName, 
	CollaborationPriorityCodeType.listID, 
	CollaborationPriorityCodeType.listName, 
	CollaborationPriorityCodeType.listSchemeURI, 
	CollaborationPriorityCodeType.listURI, 
	CollaborationPriorityCodeType.listVersionID, 
	CollaborationPriorityCodeType.name, CommentType.languageID, 
	CommentType.languageLocaleID, CommodityCodeType.languageID, 
	CommodityCodeType.listAgencyID, CommodityCodeType.listAgencyName, 
	CommodityCodeType.listID, CommodityCodeType.listName, 
	CommodityCodeType.listSchemeURI, CommodityCodeType.listURI, 
	CommodityCodeType.listVersionID, CommodityCodeType.name, 
	CompanyIDType.schemeAgencyID, CompanyIDType.schemeAgencyName, 
	CompanyIDType.schemeDataURI, CompanyIDType.schemeID, 
	CompanyIDType.schemeName, CompanyIDType.schemeURI, 
	CompanyIDType.schemeVersionID, CompanyLegalFormCodeType.languageID, 
	CompanyLegalFormCodeType.listAgencyID, 
	CompanyLegalFormCodeType.listAgencyName, 
	CompanyLegalFormCodeType.listID, CompanyLegalFormCodeType.listName, 
	CompanyLegalFormCodeType.listSchemeURI, 
	CompanyLegalFormCodeType.listURI, 
	CompanyLegalFormCodeType.listVersionID, CompanyLegalFormCodeType.name,
	CompanyLiquidationStatusCodeType.languageID, 
	CompanyLiquidationStatusCodeType.listAgencyID, 
	CompanyLiquidationStatusCodeType.listAgencyName, 
	CompanyLiquidationStatusCodeType.listID, 
	CompanyLiquidationStatusCodeType.listName, 
	CompanyLiquidationStatusCodeType.listSchemeURI, 
	CompanyLiquidationStatusCodeType.listURI, 
	CompanyLiquidationStatusCodeType.listVersionID, 
	CompanyLiquidationStatusCodeType.name, 
	ComparedValueMeasureType.unitCode, 
	ComparedValueMeasureType.unitCodeListVersionID, 
	ComparisonDataCodeType.languageID, 
	ComparisonDataCodeType.listAgencyID, 
	ComparisonDataCodeType.listAgencyName, ComparisonDataCodeType.listID, 
	ComparisonDataCodeType.listName, ComparisonDataCodeType.listSchemeURI,
	ComparisonDataCodeType.listURI, ComparisonDataCodeType.listVersionID, 
	ComparisonDataCodeType.name, ComparisonDataSourceCodeType.languageID, 
	ComparisonDataSourceCodeType.listAgencyID, 
	ComparisonDataSourceCodeType.listAgencyName, 
	ComparisonDataSourceCodeType.listID, 
	ComparisonDataSourceCodeType.listName, 
	ComparisonDataSourceCodeType.listSchemeURI, 
	ComparisonDataSourceCodeType.listURI, 
	ComparisonDataSourceCodeType.listVersionID, 
	ComparisonDataSourceCodeType.name, ConditionCodeType.languageID, 
	ConditionCodeType.listAgencyID, ConditionCodeType.listAgencyName, 
	ConditionCodeType.listID, ConditionCodeType.listName, 
	ConditionCodeType.listSchemeURI, ConditionCodeType.listURI, 
	ConditionCodeType.listVersionID, ConditionCodeType.name, 
	ConditionType.languageID, ConditionType.languageLocaleID, 
	ConditionValueMeasureType.unitCode, 
	ConditionValueMeasureType.unitCodeListVersionID, 
	ConditionsDescriptionType.languageID, 
	ConditionsDescriptionType.languageLocaleID, ConditionsType.languageID,
	ConditionsType.languageLocaleID, 
	ConsigneeAssignedIDType.schemeAgencyID, 
	ConsigneeAssignedIDType.schemeAgencyName, 
	ConsigneeAssignedIDType.schemeDataURI, 
	ConsigneeAssignedIDType.schemeID, ConsigneeAssignedIDType.schemeName, 
	ConsigneeAssignedIDType.schemeURI, 
	ConsigneeAssignedIDType.schemeVersionID, 
	ConsignmentQuantityType.unitCode, 
	ConsignmentQuantityType.unitCodeListAgencyID, 
	ConsignmentQuantityType.unitCodeListAgencyName, 
	ConsignmentQuantityType.unitCodeListID, 
	ConsignorAssignedIDType.schemeAgencyID, 
	ConsignorAssignedIDType.schemeAgencyName, 
	ConsignorAssignedIDType.schemeDataURI, 
	ConsignorAssignedIDType.schemeID, ConsignorAssignedIDType.schemeName, 
	ConsignorAssignedIDType.schemeURI, 
	ConsignorAssignedIDType.schemeVersionID, 
	ConstitutionCodeType.languageID, ConstitutionCodeType.listAgencyID, 
	ConstitutionCodeType.listAgencyName, ConstitutionCodeType.listID, 
	ConstitutionCodeType.listName, ConstitutionCodeType.listSchemeURI, 
	ConstitutionCodeType.listURI, ConstitutionCodeType.listVersionID, 
	ConstitutionCodeType.name, 
	ConsumerIncentiveTacticTypeCodeType.languageID, 
	ConsumerIncentiveTacticTypeCodeType.listAgencyID, 
	ConsumerIncentiveTacticTypeCodeType.listAgencyName, 
	ConsumerIncentiveTacticTypeCodeType.listID, 
	ConsumerIncentiveTacticTypeCodeType.listName, 
	ConsumerIncentiveTacticTypeCodeType.listSchemeURI, 
	ConsumerIncentiveTacticTypeCodeType.listURI, 
	ConsumerIncentiveTacticTypeCodeType.listVersionID, 
	ConsumerIncentiveTacticTypeCodeType.name, 
	ConsumerUnitQuantityType.unitCode, 
	ConsumerUnitQuantityType.unitCodeListAgencyID, 
	ConsumerUnitQuantityType.unitCodeListAgencyName, 
	ConsumerUnitQuantityType.unitCodeListID, 
	ConsumersEnergyLevelCodeType.languageID, 
	ConsumersEnergyLevelCodeType.listAgencyID, 
	ConsumersEnergyLevelCodeType.listAgencyName, 
	ConsumersEnergyLevelCodeType.listID, 
	ConsumersEnergyLevelCodeType.listName, 
	ConsumersEnergyLevelCodeType.listSchemeURI, 
	ConsumersEnergyLevelCodeType.listURI, 
	ConsumersEnergyLevelCodeType.listVersionID, 
	ConsumersEnergyLevelCodeType.name, 
	ConsumersEnergyLevelType.languageID, 
	ConsumersEnergyLevelType.languageLocaleID, 
	ConsumptionEnergyQuantityType.unitCode, 
	ConsumptionEnergyQuantityType.unitCodeListAgencyID, 
	ConsumptionEnergyQuantityType.unitCodeListAgencyName, 
	ConsumptionEnergyQuantityType.unitCodeListID, 
	ConsumptionIDType.schemeAgencyID, ConsumptionIDType.schemeAgencyName, 
	ConsumptionIDType.schemeDataURI, ConsumptionIDType.schemeID, 
	ConsumptionIDType.schemeName, ConsumptionIDType.schemeURI, 
	ConsumptionIDType.schemeVersionID, 
	ConsumptionLevelCodeType.languageID, 
	ConsumptionLevelCodeType.listAgencyID, 
	ConsumptionLevelCodeType.listAgencyName, 
	ConsumptionLevelCodeType.listID, ConsumptionLevelCodeType.listName, 
	ConsumptionLevelCodeType.listSchemeURI, 
	ConsumptionLevelCodeType.listURI, 
	ConsumptionLevelCodeType.listVersionID, ConsumptionLevelCodeType.name,
	ConsumptionLevelType.languageID, 
	ConsumptionLevelType.languageLocaleID, 
	ConsumptionReportIDType.schemeAgencyID, 
	ConsumptionReportIDType.schemeAgencyName, 
	ConsumptionReportIDType.schemeDataURI, 
	ConsumptionReportIDType.schemeID, ConsumptionReportIDType.schemeName, 
	ConsumptionReportIDType.schemeURI, 
	ConsumptionReportIDType.schemeVersionID, 
	ConsumptionTypeCodeType.languageID, 
	ConsumptionTypeCodeType.listAgencyID, 
	ConsumptionTypeCodeType.listAgencyName, 
	ConsumptionTypeCodeType.listID, ConsumptionTypeCodeType.listName, 
	ConsumptionTypeCodeType.listSchemeURI, 
	ConsumptionTypeCodeType.listURI, 
	ConsumptionTypeCodeType.listVersionID, ConsumptionTypeCodeType.name, 
	ConsumptionTypeType.languageID, ConsumptionTypeType.languageLocaleID, 
	ConsumptionWaterQuantityType.unitCode, 
	ConsumptionWaterQuantityType.unitCodeListAgencyID, 
	ConsumptionWaterQuantityType.unitCodeListAgencyName, 
	ConsumptionWaterQuantityType.unitCodeListID, 
	ContentUnitQuantityType.unitCode, 
	ContentUnitQuantityType.unitCodeListAgencyID, 
	ContentUnitQuantityType.unitCodeListAgencyName, 
	ContentUnitQuantityType.unitCodeListID, 
	ContractFolderIDType.schemeAgencyID, 
	ContractFolderIDType.schemeAgencyName, 
	ContractFolderIDType.schemeDataURI, ContractFolderIDType.schemeID, 
	ContractFolderIDType.schemeName, ContractFolderIDType.schemeURI, 
	ContractFolderIDType.schemeVersionID, ContractNameType.languageID, 
	ContractNameType.languageLocaleID, ContractSubdivisionType.languageID,
	ContractSubdivisionType.languageLocaleID, 
	ContractTypeCodeType.languageID, ContractTypeCodeType.listAgencyID, 
	ContractTypeCodeType.listAgencyName, ContractTypeCodeType.listID, 
	ContractTypeCodeType.listName, ContractTypeCodeType.listSchemeURI, 
	ContractTypeCodeType.listURI, ContractTypeCodeType.listVersionID, 
	ContractTypeCodeType.name, ContractTypeType.languageID, 
	ContractTypeType.languageLocaleID, 
	ContractedCarrierAssignedIDType.schemeAgencyID, 
	ContractedCarrierAssignedIDType.schemeAgencyName, 
	ContractedCarrierAssignedIDType.schemeDataURI, 
	ContractedCarrierAssignedIDType.schemeID, 
	ContractedCarrierAssignedIDType.schemeName, 
	ContractedCarrierAssignedIDType.schemeURI, 
	ContractedCarrierAssignedIDType.schemeVersionID, 
	ContractingPartyTypeCodeType.languageID, 
	ContractingPartyTypeCodeType.listAgencyID, 
	ContractingPartyTypeCodeType.listAgencyName, 
	ContractingPartyTypeCodeType.listID, 
	ContractingPartyTypeCodeType.listName, 
	ContractingPartyTypeCodeType.listSchemeURI, 
	ContractingPartyTypeCodeType.listURI, 
	ContractingPartyTypeCodeType.listVersionID, 
	ContractingPartyTypeCodeType.name, 
	ContractingSystemCodeType.languageID, 
	ContractingSystemCodeType.listAgencyID, 
	ContractingSystemCodeType.listAgencyName, 
	ContractingSystemCodeType.listID, ContractingSystemCodeType.listName, 
	ContractingSystemCodeType.listSchemeURI, 
	ContractingSystemCodeType.listURI, 
	ContractingSystemCodeType.listVersionID, 
	ContractingSystemCodeType.name, CoordinateSystemCodeType.languageID, 
	CoordinateSystemCodeType.listAgencyID, 
	CoordinateSystemCodeType.listAgencyName, 
	CoordinateSystemCodeType.listID, CoordinateSystemCodeType.listName, 
	CoordinateSystemCodeType.listSchemeURI, 
	CoordinateSystemCodeType.listURI, 
	CoordinateSystemCodeType.listVersionID, CoordinateSystemCodeType.name,
	CorporateRegistrationTypeCodeType.languageID, 
	CorporateRegistrationTypeCodeType.listAgencyID, 
	CorporateRegistrationTypeCodeType.listAgencyName, 
	CorporateRegistrationTypeCodeType.listID, 
	CorporateRegistrationTypeCodeType.listName, 
	CorporateRegistrationTypeCodeType.listSchemeURI, 
	CorporateRegistrationTypeCodeType.listURI, 
	CorporateRegistrationTypeCodeType.listVersionID, 
	CorporateRegistrationTypeCodeType.name, 
	CorporateStockAmountType.currencyCodeListVersionID, 
	CorporateStockAmountType.currencyID, 
	CorrectionAmountType.currencyCodeListVersionID, 
	CorrectionAmountType.currencyID, CorrectionTypeCodeType.languageID, 
	CorrectionTypeCodeType.listAgencyID, 
	CorrectionTypeCodeType.listAgencyName, CorrectionTypeCodeType.listID, 
	CorrectionTypeCodeType.listName, CorrectionTypeCodeType.listSchemeURI,
	CorrectionTypeCodeType.listURI, CorrectionTypeCodeType.listVersionID, 
	CorrectionTypeCodeType.name, CorrectionTypeType.languageID, 
	CorrectionTypeType.languageLocaleID, 
	CorrectionUnitAmountType.currencyCodeListVersionID, 
	CorrectionUnitAmountType.currencyID, 
	CountrySubentityCodeType.languageID, 
	CountrySubentityCodeType.listAgencyID, 
	CountrySubentityCodeType.listAgencyName, 
	CountrySubentityCodeType.listID, CountrySubentityCodeType.listName, 
	CountrySubentityCodeType.listSchemeURI, 
	CountrySubentityCodeType.listURI, 
	CountrySubentityCodeType.listVersionID, CountrySubentityCodeType.name,
	CountrySubentityType.languageID, 
	CountrySubentityType.languageLocaleID, 
	CreditLineAmountType.currencyCodeListVersionID, 
	CreditLineAmountType.currencyID, CreditedQuantityType.unitCode, 
	CreditedQuantityType.unitCodeListAgencyID, 
	CreditedQuantityType.unitCodeListAgencyName, 
	CreditedQuantityType.unitCodeListID, CurrencyCodeType.languageID, 
	CurrencyCodeType.listAgencyID, CurrencyCodeType.listAgencyName, 
	CurrencyCodeType.listID, CurrencyCodeType.listName, 
	CurrencyCodeType.listSchemeURI, CurrencyCodeType.listURI, 
	CurrencyCodeType.listVersionID, CurrencyCodeType.name, 
	CurrentChargeTypeCodeType.languageID, 
	CurrentChargeTypeCodeType.listAgencyID, 
	CurrentChargeTypeCodeType.listAgencyName, 
	CurrentChargeTypeCodeType.listID, CurrentChargeTypeCodeType.listName, 
	CurrentChargeTypeCodeType.listSchemeURI, 
	CurrentChargeTypeCodeType.listURI, 
	CurrentChargeTypeCodeType.listVersionID, 
	CurrentChargeTypeCodeType.name, CurrentChargeTypeType.languageID, 
	CurrentChargeTypeType.languageLocaleID, 
	CustomerAssignedAccountIDType.schemeAgencyID, 
	CustomerAssignedAccountIDType.schemeAgencyName, 
	CustomerAssignedAccountIDType.schemeDataURI, 
	CustomerAssignedAccountIDType.schemeID, 
	CustomerAssignedAccountIDType.schemeName, 
	CustomerAssignedAccountIDType.schemeURI, 
	CustomerAssignedAccountIDType.schemeVersionID, 
	CustomerReferenceType.languageID, 
	CustomerReferenceType.languageLocaleID, 
	CustomizationIDType.schemeAgencyID, 
	CustomizationIDType.schemeAgencyName, 
	CustomizationIDType.schemeDataURI, CustomizationIDType.schemeID, 
	CustomizationIDType.schemeName, CustomizationIDType.schemeURI, 
	CustomizationIDType.schemeVersionID, 
	CustomsClearanceServiceInstructionsType.languageID, 
	CustomsClearanceServiceInstructionsType.languageLocaleID, 
	CustomsStatusCodeType.languageID, CustomsStatusCodeType.listAgencyID, 
	CustomsStatusCodeType.listAgencyName, CustomsStatusCodeType.listID, 
	CustomsStatusCodeType.listName, CustomsStatusCodeType.listSchemeURI, 
	CustomsStatusCodeType.listURI, CustomsStatusCodeType.listVersionID, 
	CustomsStatusCodeType.name, CustomsTariffQuantityType.unitCode, 
	CustomsTariffQuantityType.unitCodeListAgencyID, 
	CustomsTariffQuantityType.unitCodeListAgencyName, 
	CustomsTariffQuantityType.unitCodeListID, 
	DamageRemarksType.languageID, DamageRemarksType.languageLocaleID, 
	DataSendingCapabilityType.languageID, 
	DataSendingCapabilityType.languageLocaleID, 
	DataSourceCodeType.languageID, DataSourceCodeType.listAgencyID, 
	DataSourceCodeType.listAgencyName, DataSourceCodeType.listID, 
	DataSourceCodeType.listName, DataSourceCodeType.listSchemeURI, 
	DataSourceCodeType.listURI, DataSourceCodeType.listVersionID, 
	DataSourceCodeType.name, 
	DebitLineAmountType.currencyCodeListVersionID, 
	DebitLineAmountType.currencyID, DebitedQuantityType.unitCode, 
	DebitedQuantityType.unitCodeListAgencyID, 
	DebitedQuantityType.unitCodeListAgencyName, 
	DebitedQuantityType.unitCodeListID, 
	DeclarationTypeCodeType.languageID, 
	DeclarationTypeCodeType.listAgencyID, 
	DeclarationTypeCodeType.listAgencyName, 
	DeclarationTypeCodeType.listID, DeclarationTypeCodeType.listName, 
	DeclarationTypeCodeType.listSchemeURI, 
	DeclarationTypeCodeType.listURI, 
	DeclarationTypeCodeType.listVersionID, DeclarationTypeCodeType.name, 
	DeclaredCarriageValueAmountType.currencyCodeListVersionID, 
	DeclaredCarriageValueAmountType.currencyID, 
	DeclaredCustomsValueAmountType.currencyCodeListVersionID, 
	DeclaredCustomsValueAmountType.currencyID, 
	DeclaredForCarriageValueAmountType.currencyCodeListVersionID, 
	DeclaredForCarriageValueAmountType.currencyID, 
	DeclaredStatisticsValueAmountType.currencyCodeListVersionID, 
	DeclaredStatisticsValueAmountType.currencyID, 
	DeliveredQuantityType.unitCode, 
	DeliveredQuantityType.unitCodeListAgencyID, 
	DeliveredQuantityType.unitCodeListAgencyName, 
	DeliveredQuantityType.unitCodeListID, 
	DeliveryInstructionsType.languageID, 
	DeliveryInstructionsType.languageLocaleID, 
	DemurrageInstructionsType.languageID, 
	DemurrageInstructionsType.languageLocaleID, DepartmentType.languageID,
	DepartmentType.languageLocaleID, DescriptionCodeType.languageID, 
	DescriptionCodeType.listAgencyID, DescriptionCodeType.listAgencyName, 
	DescriptionCodeType.listID, DescriptionCodeType.listName, 
	DescriptionCodeType.listSchemeURI, DescriptionCodeType.listURI, 
	DescriptionCodeType.listVersionID, DescriptionCodeType.name, 
	DescriptionType.languageID, DescriptionType.languageLocaleID, 
	DespatchAdviceTypeCodeType.languageID, 
	DespatchAdviceTypeCodeType.listAgencyID, 
	DespatchAdviceTypeCodeType.listAgencyName, 
	DespatchAdviceTypeCodeType.listID, 
	DespatchAdviceTypeCodeType.listName, 
	DespatchAdviceTypeCodeType.listSchemeURI, 
	DespatchAdviceTypeCodeType.listURI, 
	DespatchAdviceTypeCodeType.listVersionID, 
	DespatchAdviceTypeCodeType.name, 
	DifferenceTemperatureReductionQuantityType.unitCode, 
	DifferenceTemperatureReductionQuantityType.unitCodeListAgencyID, 
	DifferenceTemperatureReductionQuantityType.unitCodeListAgencyName, 
	DifferenceTemperatureReductionQuantityType.unitCodeListID, 
	DirectionCodeType.languageID, DirectionCodeType.listAgencyID, 
	DirectionCodeType.listAgencyName, DirectionCodeType.listID, 
	DirectionCodeType.listName, DirectionCodeType.listSchemeURI, 
	DirectionCodeType.listURI, DirectionCodeType.listVersionID, 
	DirectionCodeType.name, DisplayTacticTypeCodeType.languageID, 
	DisplayTacticTypeCodeType.listAgencyID, 
	DisplayTacticTypeCodeType.listAgencyName, 
	DisplayTacticTypeCodeType.listID, DisplayTacticTypeCodeType.listName, 
	DisplayTacticTypeCodeType.listSchemeURI, 
	DisplayTacticTypeCodeType.listURI, 
	DisplayTacticTypeCodeType.listVersionID, 
	DisplayTacticTypeCodeType.name, DispositionCodeType.languageID, 
	DispositionCodeType.listAgencyID, DispositionCodeType.listAgencyName, 
	DispositionCodeType.listID, DispositionCodeType.listName, 
	DispositionCodeType.listSchemeURI, DispositionCodeType.listURI, 
	DispositionCodeType.listVersionID, DispositionCodeType.name, 
	DistrictType.languageID, DistrictType.languageLocaleID, 
	DocumentCurrencyCodeType.languageID, 
	DocumentCurrencyCodeType.listAgencyID, 
	DocumentCurrencyCodeType.listAgencyName, 
	DocumentCurrencyCodeType.listID, DocumentCurrencyCodeType.listName, 
	DocumentCurrencyCodeType.listSchemeURI, 
	DocumentCurrencyCodeType.listURI, 
	DocumentCurrencyCodeType.listVersionID, DocumentCurrencyCodeType.name,
	DocumentDescriptionType.languageID, 
	DocumentDescriptionType.languageLocaleID, DocumentHashType.languageID,
	DocumentHashType.languageLocaleID, DocumentIDType.schemeAgencyID, 
	DocumentIDType.schemeAgencyName, DocumentIDType.schemeDataURI, 
	DocumentIDType.schemeID, DocumentIDType.schemeName, 
	DocumentIDType.schemeURI, DocumentIDType.schemeVersionID, 
	DocumentStatusCodeType.languageID, 
	DocumentStatusCodeType.listAgencyID, 
	DocumentStatusCodeType.listAgencyName, DocumentStatusCodeType.listID, 
	DocumentStatusCodeType.listName, DocumentStatusCodeType.listSchemeURI,
	DocumentStatusCodeType.listURI, DocumentStatusCodeType.listVersionID, 
	DocumentStatusCodeType.name, DocumentTypeCodeType.languageID, 
	DocumentTypeCodeType.listAgencyID, 
	DocumentTypeCodeType.listAgencyName, DocumentTypeCodeType.listID, 
	DocumentTypeCodeType.listName, DocumentTypeCodeType.listSchemeURI, 
	DocumentTypeCodeType.listURI, DocumentTypeCodeType.listVersionID, 
	DocumentTypeCodeType.name, DocumentTypeType.languageID, 
	DocumentTypeType.languageLocaleID, DurationMeasureType.unitCode, 
	DurationMeasureType.unitCodeListVersionID, DutyCodeType.languageID, 
	DutyCodeType.listAgencyID, DutyCodeType.listAgencyName, 
	DutyCodeType.listID, DutyCodeType.listName, 
	DutyCodeType.listSchemeURI, DutyCodeType.listURI, 
	DutyCodeType.listVersionID, DutyCodeType.name, DutyType-1.languageID, 
	DutyType-1.languageLocaleID, 
	EconomicOperatorRegistryURIType.schemeAgencyID, 
	EconomicOperatorRegistryURIType.schemeAgencyName, 
	EconomicOperatorRegistryURIType.schemeDataURI, 
	EconomicOperatorRegistryURIType.schemeID, 
	EconomicOperatorRegistryURIType.schemeName, 
	EconomicOperatorRegistryURIType.schemeURI, 
	EconomicOperatorRegistryURIType.schemeVersionID, 
	ElectronicDeviceDescriptionType.languageID, 
	ElectronicDeviceDescriptionType.languageLocaleID, 
	ElectronicMailType.languageID, ElectronicMailType.languageLocaleID, 
	EmbeddedDocumentBinaryObjectType.characterSetCode, 
	EmbeddedDocumentBinaryObjectType.encodingCode, 
	EmbeddedDocumentBinaryObjectType.filename, 
	EmbeddedDocumentBinaryObjectType.format, 
	EmbeddedDocumentBinaryObjectType.mimeCode, 
	EmbeddedDocumentBinaryObjectType.uri, 
	EmergencyProceduresCodeType.languageID, 
	EmergencyProceduresCodeType.listAgencyID, 
	EmergencyProceduresCodeType.listAgencyName, 
	EmergencyProceduresCodeType.listID, 
	EmergencyProceduresCodeType.listName, 
	EmergencyProceduresCodeType.listSchemeURI, 
	EmergencyProceduresCodeType.listURI, 
	EmergencyProceduresCodeType.listVersionID, 
	EmergencyProceduresCodeType.name, EmployeeQuantityType.unitCode, 
	EmployeeQuantityType.unitCodeListAgencyID, 
	EmployeeQuantityType.unitCodeListAgencyName, 
	EmployeeQuantityType.unitCodeListID, EncodingCodeType.languageID, 
	EncodingCodeType.listAgencyID, EncodingCodeType.listAgencyName, 
	EncodingCodeType.listID, EncodingCodeType.listName, 
	EncodingCodeType.listSchemeURI, EncodingCodeType.listURI, 
	EncodingCodeType.listVersionID, EncodingCodeType.name, 
	EndpointIDType.schemeAgencyID, EndpointIDType.schemeAgencyName, 
	EndpointIDType.schemeDataURI, EndpointIDType.schemeID, 
	EndpointIDType.schemeName, EndpointIDType.schemeURI, 
	EndpointIDType.schemeVersionID, 
	EnvironmentalEmissionTypeCodeType.languageID, 
	EnvironmentalEmissionTypeCodeType.listAgencyID, 
	EnvironmentalEmissionTypeCodeType.listAgencyName, 
	EnvironmentalEmissionTypeCodeType.listID, 
	EnvironmentalEmissionTypeCodeType.listName, 
	EnvironmentalEmissionTypeCodeType.listSchemeURI, 
	EnvironmentalEmissionTypeCodeType.listURI, 
	EnvironmentalEmissionTypeCodeType.listVersionID, 
	EnvironmentalEmissionTypeCodeType.name, 
	EstimatedConsumedQuantityType.unitCode, 
	EstimatedConsumedQuantityType.unitCodeListAgencyID, 
	EstimatedConsumedQuantityType.unitCodeListAgencyName, 
	EstimatedConsumedQuantityType.unitCodeListID, 
	EstimatedOverallContractAmountType.currencyCodeListVersionID, 
	EstimatedOverallContractAmountType.currencyID, 
	EstimatedOverallContractQuantityType.unitCode, 
	EstimatedOverallContractQuantityType.unitCodeListAgencyID, 
	EstimatedOverallContractQuantityType.unitCodeListAgencyName, 
	EstimatedOverallContractQuantityType.unitCodeListID, 
	EvaluationCriteriaTypeCodeType.languageID, 
	EvaluationCriteriaTypeCodeType.listAgencyID, 
	EvaluationCriteriaTypeCodeType.listAgencyName, 
	EvaluationCriteriaTypeCodeType.listID, 
	EvaluationCriteriaTypeCodeType.listName, 
	EvaluationCriteriaTypeCodeType.listSchemeURI, 
	EvaluationCriteriaTypeCodeType.listURI, 
	EvaluationCriteriaTypeCodeType.listVersionID, 
	EvaluationCriteriaTypeCodeType.name, 
	EvidenceSuppliedIDType.schemeAgencyID, 
	EvidenceSuppliedIDType.schemeAgencyName, 
	EvidenceSuppliedIDType.schemeDataURI, EvidenceSuppliedIDType.schemeID,
	EvidenceSuppliedIDType.schemeName, EvidenceSuppliedIDType.schemeURI, 
	EvidenceSuppliedIDType.schemeVersionID, 
	EvidenceTypeCodeType.languageID, EvidenceTypeCodeType.listAgencyID, 
	EvidenceTypeCodeType.listAgencyName, EvidenceTypeCodeType.listID, 
	EvidenceTypeCodeType.listName, EvidenceTypeCodeType.listSchemeURI, 
	EvidenceTypeCodeType.listURI, EvidenceTypeCodeType.listVersionID, 
	EvidenceTypeCodeType.name, ExceptionResolutionCodeType.languageID, 
	ExceptionResolutionCodeType.listAgencyID, 
	ExceptionResolutionCodeType.listAgencyName, 
	ExceptionResolutionCodeType.listID, 
	ExceptionResolutionCodeType.listName, 
	ExceptionResolutionCodeType.listSchemeURI, 
	ExceptionResolutionCodeType.listURI, 
	ExceptionResolutionCodeType.listVersionID, 
	ExceptionResolutionCodeType.name, ExceptionStatusCodeType.languageID, 
	ExceptionStatusCodeType.listAgencyID, 
	ExceptionStatusCodeType.listAgencyName, 
	ExceptionStatusCodeType.listID, ExceptionStatusCodeType.listName, 
	ExceptionStatusCodeType.listSchemeURI, 
	ExceptionStatusCodeType.listURI, 
	ExceptionStatusCodeType.listVersionID, ExceptionStatusCodeType.name, 
	ExchangeMarketIDType.schemeAgencyID, 
	ExchangeMarketIDType.schemeAgencyName, 
	ExchangeMarketIDType.schemeDataURI, ExchangeMarketIDType.schemeID, 
	ExchangeMarketIDType.schemeName, ExchangeMarketIDType.schemeURI, 
	ExchangeMarketIDType.schemeVersionID, ExclusionReasonType.languageID, 
	ExclusionReasonType.languageLocaleID, 
	ExecutionRequirementCodeType.languageID, 
	ExecutionRequirementCodeType.listAgencyID, 
	ExecutionRequirementCodeType.listAgencyName, 
	ExecutionRequirementCodeType.listID, 
	ExecutionRequirementCodeType.listName, 
	ExecutionRequirementCodeType.listSchemeURI, 
	ExecutionRequirementCodeType.listURI, 
	ExecutionRequirementCodeType.listVersionID, 
	ExecutionRequirementCodeType.name, ExemptionReasonCodeType.languageID,
	ExemptionReasonCodeType.listAgencyID, 
	ExemptionReasonCodeType.listAgencyName, 
	ExemptionReasonCodeType.listID, ExemptionReasonCodeType.listName, 
	ExemptionReasonCodeType.listSchemeURI, 
	ExemptionReasonCodeType.listURI, 
	ExemptionReasonCodeType.listVersionID, ExemptionReasonCodeType.name, 
	ExemptionReasonType.languageID, ExemptionReasonType.languageLocaleID, 
	ExpectedOperatorQuantityType.unitCode, 
	ExpectedOperatorQuantityType.unitCodeListAgencyID, 
	ExpectedOperatorQuantityType.unitCodeListAgencyName, 
	ExpectedOperatorQuantityType.unitCodeListID, 
	ExpectedQuantityType.unitCode, 
	ExpectedQuantityType.unitCodeListAgencyID, 
	ExpectedQuantityType.unitCodeListAgencyName, 
	ExpectedQuantityType.unitCodeListID, ExpenseCodeType.languageID, 
	ExpenseCodeType.listAgencyID, ExpenseCodeType.listAgencyName, 
	ExpenseCodeType.listID, ExpenseCodeType.listName, 
	ExpenseCodeType.listSchemeURI, ExpenseCodeType.listURI, 
	ExpenseCodeType.listVersionID, ExpenseCodeType.name, 
	ExpressionCodeType.languageID, ExpressionCodeType.listAgencyID, 
	ExpressionCodeType.listAgencyName, ExpressionCodeType.listID, 
	ExpressionCodeType.listName, ExpressionCodeType.listSchemeURI, 
	ExpressionCodeType.listURI, ExpressionCodeType.listVersionID, 
	ExpressionCodeType.name, ExtendedIDType.schemeAgencyID, 
	ExtendedIDType.schemeAgencyName, ExtendedIDType.schemeDataURI, 
	ExtendedIDType.schemeID, ExtendedIDType.schemeName, 
	ExtendedIDType.schemeURI, ExtendedIDType.schemeVersionID, 
	ExtensionType.languageID, ExtensionType.languageLocaleID, 
	FaceValueAmountType.currencyCodeListVersionID, 
	FaceValueAmountType.currencyID, FamilyNameType.languageID, 
	FamilyNameType.languageLocaleID, FeatureTacticTypeCodeType.languageID,
	FeatureTacticTypeCodeType.listAgencyID, 
	FeatureTacticTypeCodeType.listAgencyName, 
	FeatureTacticTypeCodeType.listID, FeatureTacticTypeCodeType.listName, 
	FeatureTacticTypeCodeType.listSchemeURI, 
	FeatureTacticTypeCodeType.listURI, 
	FeatureTacticTypeCodeType.listVersionID, 
	FeatureTacticTypeCodeType.name, 
	FeeAmountType.currencyCodeListVersionID, FeeAmountType.currencyID, 
	FeeDescriptionType.languageID, FeeDescriptionType.languageLocaleID, 
	FileNameType.languageID, FileNameType.languageLocaleID, 
	FinancingInstrumentCodeType.languageID, 
	FinancingInstrumentCodeType.listAgencyID, 
	FinancingInstrumentCodeType.listAgencyName, 
	FinancingInstrumentCodeType.listID, 
	FinancingInstrumentCodeType.listName, 
	FinancingInstrumentCodeType.listSchemeURI, 
	FinancingInstrumentCodeType.listURI, 
	FinancingInstrumentCodeType.listVersionID, 
	FinancingInstrumentCodeType.name, FirstNameType.languageID, 
	FirstNameType.languageLocaleID, FloorType.languageID, 
	FloorType.languageLocaleID, ForecastPurposeCodeType.languageID, 
	ForecastPurposeCodeType.listAgencyID, 
	ForecastPurposeCodeType.listAgencyName, 
	ForecastPurposeCodeType.listID, ForecastPurposeCodeType.listName, 
	ForecastPurposeCodeType.listSchemeURI, 
	ForecastPurposeCodeType.listURI, 
	ForecastPurposeCodeType.listVersionID, ForecastPurposeCodeType.name, 
	ForecastTypeCodeType.languageID, ForecastTypeCodeType.listAgencyID, 
	ForecastTypeCodeType.listAgencyName, ForecastTypeCodeType.listID, 
	ForecastTypeCodeType.listName, ForecastTypeCodeType.listSchemeURI, 
	ForecastTypeCodeType.listURI, ForecastTypeCodeType.listVersionID, 
	ForecastTypeCodeType.name, FormatCodeType.languageID, 
	FormatCodeType.listAgencyID, FormatCodeType.listAgencyName, 
	FormatCodeType.listID, FormatCodeType.listName, 
	FormatCodeType.listSchemeURI, FormatCodeType.listURI, 
	FormatCodeType.listVersionID, FormatCodeType.name, 
	ForwarderServiceInstructionsType.languageID, 
	ForwarderServiceInstructionsType.languageLocaleID, 
	FreeOnBoardValueAmountType.currencyCodeListVersionID, 
	FreeOnBoardValueAmountType.currencyID, 
	FreightForwarderAssignedIDType.schemeAgencyID, 
	FreightForwarderAssignedIDType.schemeAgencyName, 
	FreightForwarderAssignedIDType.schemeDataURI, 
	FreightForwarderAssignedIDType.schemeID, 
	FreightForwarderAssignedIDType.schemeName, 
	FreightForwarderAssignedIDType.schemeURI, 
	FreightForwarderAssignedIDType.schemeVersionID, 
	FreightRateClassCodeType.languageID, 
	FreightRateClassCodeType.listAgencyID, 
	FreightRateClassCodeType.listAgencyName, 
	FreightRateClassCodeType.listID, FreightRateClassCodeType.listName, 
	FreightRateClassCodeType.listSchemeURI, 
	FreightRateClassCodeType.listURI, 
	FreightRateClassCodeType.listVersionID, FreightRateClassCodeType.name,
	FrequencyType.languageID, FrequencyType.languageLocaleID, 
	FrozenPeriodDaysNumericType.format, 
	FullnessIndicationCodeType.languageID, 
	FullnessIndicationCodeType.listAgencyID, 
	FullnessIndicationCodeType.listAgencyName, 
	FullnessIndicationCodeType.listID, 
	FullnessIndicationCodeType.listName, 
	FullnessIndicationCodeType.listSchemeURI, 
	FullnessIndicationCodeType.listURI, 
	FullnessIndicationCodeType.listVersionID, 
	FullnessIndicationCodeType.name, FundingProgramCodeType.languageID, 
	FundingProgramCodeType.listAgencyID, 
	FundingProgramCodeType.listAgencyName, FundingProgramCodeType.listID, 
	FundingProgramCodeType.listName, FundingProgramCodeType.listSchemeURI,
	FundingProgramCodeType.listURI, FundingProgramCodeType.listVersionID, 
	FundingProgramCodeType.name, FundingProgramType.languageID, 
	FundingProgramType.languageLocaleID, GasPressureQuantityType.unitCode,
	GasPressureQuantityType.unitCodeListAgencyID, 
	GasPressureQuantityType.unitCodeListAgencyName, 
	GasPressureQuantityType.unitCodeListID, GenderCodeType.languageID, 
	GenderCodeType.listAgencyID, GenderCodeType.listAgencyName, 
	GenderCodeType.listID, GenderCodeType.listName, 
	GenderCodeType.listSchemeURI, GenderCodeType.listURI, 
	GenderCodeType.listVersionID, GenderCodeType.name, 
	GrossVolumeMeasureType.unitCode, 
	GrossVolumeMeasureType.unitCodeListVersionID, 
	GrossWeightMeasureType.unitCode, 
	GrossWeightMeasureType.unitCodeListVersionID, 
	GuaranteeTypeCodeType.languageID, GuaranteeTypeCodeType.listAgencyID, 
	GuaranteeTypeCodeType.listAgencyName, GuaranteeTypeCodeType.listID, 
	GuaranteeTypeCodeType.listName, GuaranteeTypeCodeType.listSchemeURI, 
	GuaranteeTypeCodeType.listURI, GuaranteeTypeCodeType.listVersionID, 
	GuaranteeTypeCodeType.name, HandlingCodeType.languageID, 
	HandlingCodeType.listAgencyID, HandlingCodeType.listAgencyName, 
	HandlingCodeType.listID, HandlingCodeType.listName, 
	HandlingCodeType.listSchemeURI, HandlingCodeType.listURI, 
	HandlingCodeType.listVersionID, HandlingCodeType.name, 
	HandlingInstructionsType.languageID, 
	HandlingInstructionsType.languageLocaleID, 
	HashAlgorithmMethodType.languageID, 
	HashAlgorithmMethodType.languageLocaleID, 
	HaulageInstructionsType.languageID, 
	HaulageInstructionsType.languageLocaleID, 
	HazardClassIDType.schemeAgencyID, HazardClassIDType.schemeAgencyName, 
	HazardClassIDType.schemeDataURI, HazardClassIDType.schemeID, 
	HazardClassIDType.schemeName, HazardClassIDType.schemeURI, 
	HazardClassIDType.schemeVersionID, 
	HazardousCategoryCodeType.languageID, 
	HazardousCategoryCodeType.listAgencyID, 
	HazardousCategoryCodeType.listAgencyName, 
	HazardousCategoryCodeType.listID, HazardousCategoryCodeType.listName, 
	HazardousCategoryCodeType.listSchemeURI, 
	HazardousCategoryCodeType.listURI, 
	HazardousCategoryCodeType.listVersionID, 
	HazardousCategoryCodeType.name, 
	HazardousRegulationCodeType.languageID, 
	HazardousRegulationCodeType.listAgencyID, 
	HazardousRegulationCodeType.listAgencyName, 
	HazardousRegulationCodeType.listID, 
	HazardousRegulationCodeType.listName, 
	HazardousRegulationCodeType.listSchemeURI, 
	HazardousRegulationCodeType.listURI, 
	HazardousRegulationCodeType.listVersionID, 
	HazardousRegulationCodeType.name, HeatingTypeCodeType.languageID, 
	HeatingTypeCodeType.listAgencyID, HeatingTypeCodeType.listAgencyName, 
	HeatingTypeCodeType.listID, HeatingTypeCodeType.listName, 
	HeatingTypeCodeType.listSchemeURI, HeatingTypeCodeType.listURI, 
	HeatingTypeCodeType.listVersionID, HeatingTypeCodeType.name, 
	HeatingTypeType.languageID, HeatingTypeType.languageLocaleID, 
	HigherTenderAmountType.currencyCodeListVersionID, 
	HigherTenderAmountType.currencyID, HolderNameType.languageID, 
	HolderNameType.languageLocaleID, HumidityPercentType.format, 
	IDType.schemeAgencyID, IDType.schemeAgencyName, IDType.schemeDataURI, 
	IDType.schemeID, IDType.schemeName, IDType.schemeURI, 
	IDType.schemeVersionID, IdentificationCodeType.languageID, 
	IdentificationCodeType.listAgencyID, 
	IdentificationCodeType.listAgencyName, IdentificationCodeType.listID, 
	IdentificationCodeType.listName, IdentificationCodeType.listSchemeURI,
	IdentificationCodeType.listURI, IdentificationCodeType.listVersionID, 
	IdentificationCodeType.name, IdentificationIDType.schemeAgencyID, 
	IdentificationIDType.schemeAgencyName, 
	IdentificationIDType.schemeDataURI, IdentificationIDType.schemeID, 
	IdentificationIDType.schemeName, IdentificationIDType.schemeURI, 
	IdentificationIDType.schemeVersionID, 
	ImmobilizationCertificateIDType.schemeAgencyID, 
	ImmobilizationCertificateIDType.schemeAgencyName, 
	ImmobilizationCertificateIDType.schemeDataURI, 
	ImmobilizationCertificateIDType.schemeID, 
	ImmobilizationCertificateIDType.schemeName, 
	ImmobilizationCertificateIDType.schemeURI, 
	ImmobilizationCertificateIDType.schemeVersionID, 
	ImportanceCodeType.languageID, ImportanceCodeType.listAgencyID, 
	ImportanceCodeType.listAgencyName, ImportanceCodeType.listID, 
	ImportanceCodeType.listName, ImportanceCodeType.listSchemeURI, 
	ImportanceCodeType.listURI, ImportanceCodeType.listVersionID, 
	ImportanceCodeType.name, IndustryClassificationCodeType.languageID, 
	IndustryClassificationCodeType.listAgencyID, 
	IndustryClassificationCodeType.listAgencyName, 
	IndustryClassificationCodeType.listID, 
	IndustryClassificationCodeType.listName, 
	IndustryClassificationCodeType.listSchemeURI, 
	IndustryClassificationCodeType.listURI, 
	IndustryClassificationCodeType.listVersionID, 
	IndustryClassificationCodeType.name, InformationType.languageID, 
	InformationType.languageLocaleID, InformationURIType.schemeAgencyID, 
	InformationURIType.schemeAgencyName, InformationURIType.schemeDataURI,
	InformationURIType.schemeID, InformationURIType.schemeName, 
	InformationURIType.schemeURI, InformationURIType.schemeVersionID, 
	InhalationToxicityZoneCodeType.languageID, 
	InhalationToxicityZoneCodeType.listAgencyID, 
	InhalationToxicityZoneCodeType.listAgencyName, 
	InhalationToxicityZoneCodeType.listID, 
	InhalationToxicityZoneCodeType.listName, 
	InhalationToxicityZoneCodeType.listSchemeURI, 
	InhalationToxicityZoneCodeType.listURI, 
	InhalationToxicityZoneCodeType.listVersionID, 
	InhalationToxicityZoneCodeType.name, InhouseMailType.languageID, 
	InhouseMailType.languageLocaleID, InspectionMethodCodeType.languageID,
	InspectionMethodCodeType.listAgencyID, 
	InspectionMethodCodeType.listAgencyName, 
	InspectionMethodCodeType.listID, InspectionMethodCodeType.listName, 
	InspectionMethodCodeType.listSchemeURI, 
	InspectionMethodCodeType.listURI, 
	InspectionMethodCodeType.listVersionID, InspectionMethodCodeType.name,
	InstructionIDType.schemeAgencyID, InstructionIDType.schemeAgencyName, 
	InstructionIDType.schemeDataURI, InstructionIDType.schemeID, 
	InstructionIDType.schemeName, InstructionIDType.schemeURI, 
	InstructionIDType.schemeVersionID, InstructionNoteType.languageID, 
	InstructionNoteType.languageLocaleID, InstructionsType.languageID, 
	InstructionsType.languageLocaleID, 
	InsurancePremiumAmountType.currencyCodeListVersionID, 
	InsurancePremiumAmountType.currencyID, 
	InsuranceValueAmountType.currencyCodeListVersionID, 
	InsuranceValueAmountType.currencyID, 
	InterestedProcurementLotsIDType.schemeAgencyID, 
	InterestedProcurementLotsIDType.schemeAgencyName, 
	InterestedProcurementLotsIDType.schemeDataURI, 
	InterestedProcurementLotsIDType.schemeID, 
	InterestedProcurementLotsIDType.schemeName, 
	InterestedProcurementLotsIDType.schemeURI, 
	InterestedProcurementLotsIDType.schemeVersionID, 
	InventoryValueAmountType.currencyCodeListVersionID, 
	InventoryValueAmountType.currencyID, InvoiceTypeCodeType.languageID, 
	InvoiceTypeCodeType.listAgencyID, InvoiceTypeCodeType.listAgencyName, 
	InvoiceTypeCodeType.listID, InvoiceTypeCodeType.listName, 
	InvoiceTypeCodeType.listSchemeURI, InvoiceTypeCodeType.listURI, 
	InvoiceTypeCodeType.listVersionID, InvoiceTypeCodeType.name, 
	InvoicedQuantityType.unitCode, 
	InvoicedQuantityType.unitCodeListAgencyID, 
	InvoicedQuantityType.unitCodeListAgencyName, 
	InvoicedQuantityType.unitCodeListID, 
	InvoicingPartyReferenceType.languageID, 
	InvoicingPartyReferenceType.languageLocaleID, 
	IssueNumberIDType.schemeAgencyID, IssueNumberIDType.schemeAgencyName, 
	IssueNumberIDType.schemeDataURI, IssueNumberIDType.schemeID, 
	IssueNumberIDType.schemeName, IssueNumberIDType.schemeURI, 
	IssueNumberIDType.schemeVersionID, IssuerIDType.schemeAgencyID, 
	IssuerIDType.schemeAgencyName, IssuerIDType.schemeDataURI, 
	IssuerIDType.schemeID, IssuerIDType.schemeName, 
	IssuerIDType.schemeURI, IssuerIDType.schemeVersionID, 
	ItemClassificationCodeType.languageID, 
	ItemClassificationCodeType.listAgencyID, 
	ItemClassificationCodeType.listAgencyName, 
	ItemClassificationCodeType.listID, 
	ItemClassificationCodeType.listName, 
	ItemClassificationCodeType.listSchemeURI, 
	ItemClassificationCodeType.listURI, 
	ItemClassificationCodeType.listVersionID, 
	ItemClassificationCodeType.name, JobTitleType.languageID, 
	JobTitleType.languageLocaleID, JourneyIDType.schemeAgencyID, 
	JourneyIDType.schemeAgencyName, JourneyIDType.schemeDataURI, 
	JourneyIDType.schemeID, JourneyIDType.schemeName, 
	JourneyIDType.schemeURI, JourneyIDType.schemeVersionID, 
	JustificationDescriptionType.languageID, 
	JustificationDescriptionType.languageLocaleID, 
	JustificationType.languageID, JustificationType.languageLocaleID, 
	KeywordType.languageID, KeywordType.languageLocaleID, 
	LanguageIDType.schemeAgencyID, LanguageIDType.schemeAgencyName, 
	LanguageIDType.schemeDataURI, LanguageIDType.schemeID, 
	LanguageIDType.schemeName, LanguageIDType.schemeURI, 
	LanguageIDType.schemeVersionID, LatestMeterQuantityType.unitCode, 
	LatestMeterQuantityType.unitCodeListAgencyID, 
	LatestMeterQuantityType.unitCodeListAgencyName, 
	LatestMeterQuantityType.unitCodeListID, 
	LatitudeDegreesMeasureType.unitCode, 
	LatitudeDegreesMeasureType.unitCodeListVersionID, 
	LatitudeDirectionCodeType.languageID, 
	LatitudeDirectionCodeType.listAgencyID, 
	LatitudeDirectionCodeType.listAgencyName, 
	LatitudeDirectionCodeType.listID, LatitudeDirectionCodeType.listName, 
	LatitudeDirectionCodeType.listSchemeURI, 
	LatitudeDirectionCodeType.listURI, 
	LatitudeDirectionCodeType.listVersionID, 
	LatitudeDirectionCodeType.name, LatitudeMinutesMeasureType.unitCode, 
	LatitudeMinutesMeasureType.unitCodeListVersionID, 
	LeadTimeMeasureType.unitCode, 
	LeadTimeMeasureType.unitCodeListVersionID, LegalFormType.languageID, 
	LegalFormType.languageLocaleID, LegalReferenceType.languageID, 
	LegalReferenceType.languageLocaleID, 
	LiabilityAmountType.currencyCodeListVersionID, 
	LiabilityAmountType.currencyID, LicensePlateIDType.schemeAgencyID, 
	LicensePlateIDType.schemeAgencyName, LicensePlateIDType.schemeDataURI,
	LicensePlateIDType.schemeID, LicensePlateIDType.schemeName, 
	LicensePlateIDType.schemeURI, LicensePlateIDType.schemeVersionID, 
	LifeCycleStatusCodeType.languageID, 
	LifeCycleStatusCodeType.listAgencyID, 
	LifeCycleStatusCodeType.listAgencyName, 
	LifeCycleStatusCodeType.listID, LifeCycleStatusCodeType.listName, 
	LifeCycleStatusCodeType.listSchemeURI, 
	LifeCycleStatusCodeType.listURI, 
	LifeCycleStatusCodeType.listVersionID, LifeCycleStatusCodeType.name, 
	LimitationDescriptionType.languageID, 
	LimitationDescriptionType.languageLocaleID, 
	LineCountNumericType.format, 
	LineExtensionAmountType.currencyCodeListVersionID, 
	LineExtensionAmountType.currencyID, LineIDType.schemeAgencyID, 
	LineIDType.schemeAgencyName, LineIDType.schemeDataURI, 
	LineIDType.schemeID, LineIDType.schemeName, LineIDType.schemeURI, 
	LineIDType.schemeVersionID, LineNumberNumericType.format, 
	LineStatusCodeType.languageID, LineStatusCodeType.listAgencyID, 
	LineStatusCodeType.listAgencyName, LineStatusCodeType.listID, 
	LineStatusCodeType.listName, LineStatusCodeType.listSchemeURI, 
	LineStatusCodeType.listURI, LineStatusCodeType.listVersionID, 
	LineStatusCodeType.name, LineType.languageID, 
	LineType.languageLocaleID, ListValueType.languageID, 
	ListValueType.languageLocaleID, LoadingLengthMeasureType.unitCode, 
	LoadingLengthMeasureType.unitCodeListVersionID, 
	LoadingSequenceIDType.schemeAgencyID, 
	LoadingSequenceIDType.schemeAgencyName, 
	LoadingSequenceIDType.schemeDataURI, LoadingSequenceIDType.schemeID, 
	LoadingSequenceIDType.schemeName, LoadingSequenceIDType.schemeURI, 
	LoadingSequenceIDType.schemeVersionID, LocaleCodeType.languageID, 
	LocaleCodeType.listAgencyID, LocaleCodeType.listAgencyName, 
	LocaleCodeType.listID, LocaleCodeType.listName, 
	LocaleCodeType.listSchemeURI, LocaleCodeType.listURI, 
	LocaleCodeType.listVersionID, LocaleCodeType.name, 
	LocationIDType.schemeAgencyID, LocationIDType.schemeAgencyName, 
	LocationIDType.schemeDataURI, LocationIDType.schemeID, 
	LocationIDType.schemeName, LocationIDType.schemeURI, 
	LocationIDType.schemeVersionID, LocationType-1.languageID, 
	LocationType-1.languageLocaleID, LocationTypeCodeType.languageID, 
	LocationTypeCodeType.listAgencyID, 
	LocationTypeCodeType.listAgencyName, LocationTypeCodeType.listID, 
	LocationTypeCodeType.listName, LocationTypeCodeType.listSchemeURI, 
	LocationTypeCodeType.listURI, LocationTypeCodeType.listVersionID, 
	LocationTypeCodeType.name, LoginType.languageID, 
	LoginType.languageLocaleID, LogoReferenceIDType.schemeAgencyID, 
	LogoReferenceIDType.schemeAgencyName, 
	LogoReferenceIDType.schemeDataURI, LogoReferenceIDType.schemeID, 
	LogoReferenceIDType.schemeName, LogoReferenceIDType.schemeURI, 
	LogoReferenceIDType.schemeVersionID, 
	LongitudeDegreesMeasureType.unitCode, 
	LongitudeDegreesMeasureType.unitCodeListVersionID, 
	LongitudeDirectionCodeType.languageID, 
	LongitudeDirectionCodeType.listAgencyID, 
	LongitudeDirectionCodeType.listAgencyName, 
	LongitudeDirectionCodeType.listID, 
	LongitudeDirectionCodeType.listName, 
	LongitudeDirectionCodeType.listSchemeURI, 
	LongitudeDirectionCodeType.listURI, 
	LongitudeDirectionCodeType.listVersionID, 
	LongitudeDirectionCodeType.name, LongitudeMinutesMeasureType.unitCode,
	LongitudeMinutesMeasureType.unitCodeListVersionID, 
	LossRiskResponsibilityCodeType.languageID, 
	LossRiskResponsibilityCodeType.listAgencyID, 
	LossRiskResponsibilityCodeType.listAgencyName, 
	LossRiskResponsibilityCodeType.listID, 
	LossRiskResponsibilityCodeType.listName, 
	LossRiskResponsibilityCodeType.listSchemeURI, 
	LossRiskResponsibilityCodeType.listURI, 
	LossRiskResponsibilityCodeType.listVersionID, 
	LossRiskResponsibilityCodeType.name, LossRiskType.languageID, 
	LossRiskType.languageLocaleID, LotNumberIDType.schemeAgencyID, 
	LotNumberIDType.schemeAgencyName, LotNumberIDType.schemeDataURI, 
	LotNumberIDType.schemeID, LotNumberIDType.schemeName, 
	LotNumberIDType.schemeURI, LotNumberIDType.schemeVersionID, 
	LowTendersDescriptionType.languageID, 
	LowTendersDescriptionType.languageLocaleID, 
	LowerOrangeHazardPlacardIDType.schemeAgencyID, 
	LowerOrangeHazardPlacardIDType.schemeAgencyName, 
	LowerOrangeHazardPlacardIDType.schemeDataURI, 
	LowerOrangeHazardPlacardIDType.schemeID, 
	LowerOrangeHazardPlacardIDType.schemeName, 
	LowerOrangeHazardPlacardIDType.schemeURI, 
	LowerOrangeHazardPlacardIDType.schemeVersionID, 
	LowerTenderAmountType.currencyCodeListVersionID, 
	LowerTenderAmountType.currencyID, MandateTypeCodeType.languageID, 
	MandateTypeCodeType.listAgencyID, MandateTypeCodeType.listAgencyName, 
	MandateTypeCodeType.listID, MandateTypeCodeType.listName, 
	MandateTypeCodeType.listSchemeURI, MandateTypeCodeType.listURI, 
	MandateTypeCodeType.listVersionID, MandateTypeCodeType.name, 
	MarkAttentionType.languageID, MarkAttentionType.languageLocaleID, 
	MarkCareType.languageID, MarkCareType.languageLocaleID, 
	MarketValueAmountType.currencyCodeListVersionID, 
	MarketValueAmountType.currencyID, MarkingIDType.schemeAgencyID, 
	MarkingIDType.schemeAgencyName, MarkingIDType.schemeDataURI, 
	MarkingIDType.schemeID, MarkingIDType.schemeName, 
	MarkingIDType.schemeURI, MarkingIDType.schemeVersionID, 
	MathematicOperatorCodeType.languageID, 
	MathematicOperatorCodeType.listAgencyID, 
	MathematicOperatorCodeType.listAgencyName, 
	MathematicOperatorCodeType.listID, 
	MathematicOperatorCodeType.listName, 
	MathematicOperatorCodeType.listSchemeURI, 
	MathematicOperatorCodeType.listURI, 
	MathematicOperatorCodeType.listVersionID, 
	MathematicOperatorCodeType.name, 
	MaximumAdvertisementAmountType.currencyCodeListVersionID, 
	MaximumAdvertisementAmountType.currencyID, 
	MaximumAmountType.currencyCodeListVersionID, 
	MaximumAmountType.currencyID, MaximumBackorderQuantityType.unitCode, 
	MaximumBackorderQuantityType.unitCodeListAgencyID, 
	MaximumBackorderQuantityType.unitCodeListAgencyName, 
	MaximumBackorderQuantityType.unitCodeListID, 
	MaximumCopiesNumericType.format, MaximumMeasureType.unitCode, 
	MaximumMeasureType.unitCodeListVersionID, 
	MaximumNumberNumericType.format, MaximumOperatorQuantityType.unitCode,
	MaximumOperatorQuantityType.unitCodeListAgencyID, 
	MaximumOperatorQuantityType.unitCodeListAgencyName, 
	MaximumOperatorQuantityType.unitCodeListID, 
	MaximumOrderQuantityType.unitCode, 
	MaximumOrderQuantityType.unitCodeListAgencyID, 
	MaximumOrderQuantityType.unitCodeListAgencyName, 
	MaximumOrderQuantityType.unitCodeListID, 
	MaximumPaidAmountType.currencyCodeListVersionID, 
	MaximumPaidAmountType.currencyID, 
	MaximumPaymentInstructionsNumericType.format, 
	MaximumQuantityType.unitCode, 
	MaximumQuantityType.unitCodeListAgencyID, 
	MaximumQuantityType.unitCodeListAgencyName, 
	MaximumQuantityType.unitCodeListID, 
	MaximumTaxExclusiveAmountType.currencyCodeListVersionID, 
	MaximumTaxExclusiveAmountType.currencyID, 
	MaximumTaxInclusiveAmountType.currencyCodeListVersionID, 
	MaximumTaxInclusiveAmountType.currencyID, MaximumValueType.languageID,
	MaximumValueType.languageLocaleID, 
	MaximumVariantQuantityType.unitCode, 
	MaximumVariantQuantityType.unitCodeListAgencyID, 
	MaximumVariantQuantityType.unitCodeListAgencyName, 
	MaximumVariantQuantityType.unitCodeListID, MeasureType.unitCode, 
	MeasureType.unitCodeListVersionID, 
	MedicalFirstAidGuideCodeType.languageID, 
	MedicalFirstAidGuideCodeType.listAgencyID, 
	MedicalFirstAidGuideCodeType.listAgencyName, 
	MedicalFirstAidGuideCodeType.listID, 
	MedicalFirstAidGuideCodeType.listName, 
	MedicalFirstAidGuideCodeType.listSchemeURI, 
	MedicalFirstAidGuideCodeType.listURI, 
	MedicalFirstAidGuideCodeType.listVersionID, 
	MedicalFirstAidGuideCodeType.name, MeterConstantCodeType.languageID, 
	MeterConstantCodeType.listAgencyID, 
	MeterConstantCodeType.listAgencyName, MeterConstantCodeType.listID, 
	MeterConstantCodeType.listName, MeterConstantCodeType.listSchemeURI, 
	MeterConstantCodeType.listURI, MeterConstantCodeType.listVersionID, 
	MeterConstantCodeType.name, MeterConstantType.languageID, 
	MeterConstantType.languageLocaleID, MeterNameType.languageID, 
	MeterNameType.languageLocaleID, MeterNumberType.languageID, 
	MeterNumberType.languageLocaleID, MeterReadingCommentsType.languageID,
	MeterReadingCommentsType.languageLocaleID, 
	MeterReadingMethodCodeType.languageID, 
	MeterReadingMethodCodeType.listAgencyID, 
	MeterReadingMethodCodeType.listAgencyName, 
	MeterReadingMethodCodeType.listID, 
	MeterReadingMethodCodeType.listName, 
	MeterReadingMethodCodeType.listSchemeURI, 
	MeterReadingMethodCodeType.listURI, 
	MeterReadingMethodCodeType.listVersionID, 
	MeterReadingMethodCodeType.name, MeterReadingMethodType.languageID, 
	MeterReadingMethodType.languageLocaleID, 
	MeterReadingTypeCodeType.languageID, 
	MeterReadingTypeCodeType.listAgencyID, 
	MeterReadingTypeCodeType.listAgencyName, 
	MeterReadingTypeCodeType.listID, MeterReadingTypeCodeType.listName, 
	MeterReadingTypeCodeType.listSchemeURI, 
	MeterReadingTypeCodeType.listURI, 
	MeterReadingTypeCodeType.listVersionID, MeterReadingTypeCodeType.name,
	MeterReadingTypeType.languageID, 
	MeterReadingTypeType.languageLocaleID, MiddleNameType.languageID, 
	MiddleNameType.languageLocaleID, MimeCodeType.languageID, 
	MimeCodeType.listAgencyID, MimeCodeType.listAgencyName, 
	MimeCodeType.listID, MimeCodeType.listName, 
	MimeCodeType.listSchemeURI, MimeCodeType.listURI, 
	MimeCodeType.listVersionID, MimeCodeType.name, 
	MinimumAmountType.currencyCodeListVersionID, 
	MinimumAmountType.currencyID, MinimumBackorderQuantityType.unitCode, 
	MinimumBackorderQuantityType.unitCodeListAgencyID, 
	MinimumBackorderQuantityType.unitCodeListAgencyName, 
	MinimumBackorderQuantityType.unitCodeListID, 
	MinimumImprovementBidType.languageID, 
	MinimumImprovementBidType.languageLocaleID, 
	MinimumInventoryQuantityType.unitCode, 
	MinimumInventoryQuantityType.unitCodeListAgencyID, 
	MinimumInventoryQuantityType.unitCodeListAgencyName, 
	MinimumInventoryQuantityType.unitCodeListID, 
	MinimumMeasureType.unitCode, MinimumMeasureType.unitCodeListVersionID,
	MinimumNumberNumericType.format, MinimumOrderQuantityType.unitCode, 
	MinimumOrderQuantityType.unitCodeListAgencyID, 
	MinimumOrderQuantityType.unitCodeListAgencyName, 
	MinimumOrderQuantityType.unitCodeListID, MinimumQuantityType.unitCode,
	MinimumQuantityType.unitCodeListAgencyID, 
	MinimumQuantityType.unitCodeListAgencyName, 
	MinimumQuantityType.unitCodeListID, MinimumValueType.languageID, 
	MinimumValueType.languageLocaleID, 
	MiscellaneousEventTypeCodeType.languageID, 
	MiscellaneousEventTypeCodeType.listAgencyID, 
	MiscellaneousEventTypeCodeType.listAgencyName, 
	MiscellaneousEventTypeCodeType.listID, 
	MiscellaneousEventTypeCodeType.listName, 
	MiscellaneousEventTypeCodeType.listSchemeURI, 
	MiscellaneousEventTypeCodeType.listURI, 
	MiscellaneousEventTypeCodeType.listVersionID, 
	MiscellaneousEventTypeCodeType.name, ModelNameType.languageID, 
	ModelNameType.languageLocaleID, MonetaryScopeType.languageID, 
	MonetaryScopeType.languageLocaleID, MovieTitleType.languageID, 
	MovieTitleType.languageLocaleID, MultipleOrderQuantityType.unitCode, 
	MultipleOrderQuantityType.unitCodeListAgencyID, 
	MultipleOrderQuantityType.unitCodeListAgencyName, 
	MultipleOrderQuantityType.unitCodeListID, 
	MultiplierFactorNumericType.format, NameCodeType.languageID, 
	NameCodeType.listAgencyID, NameCodeType.listAgencyName, 
	NameCodeType.listID, NameCodeType.listName, 
	NameCodeType.listSchemeURI, NameCodeType.listURI, 
	NameCodeType.listVersionID, NameCodeType.name, 
	NameSuffixType.languageID, NameSuffixType.languageLocaleID, 
	NameType.languageID, NameType.languageLocaleID, 
	NationalityIDType.schemeAgencyID, NationalityIDType.schemeAgencyName, 
	NationalityIDType.schemeDataURI, NationalityIDType.schemeID, 
	NationalityIDType.schemeName, NationalityIDType.schemeURI, 
	NationalityIDType.schemeVersionID, NatureCodeType.languageID, 
	NatureCodeType.listAgencyID, NatureCodeType.listAgencyName, 
	NatureCodeType.listID, NatureCodeType.listName, 
	NatureCodeType.listSchemeURI, NatureCodeType.listURI, 
	NatureCodeType.listVersionID, NatureCodeType.name, 
	NegotiationDescriptionType.languageID, 
	NegotiationDescriptionType.languageLocaleID, 
	NetNetWeightMeasureType.unitCode, 
	NetNetWeightMeasureType.unitCodeListVersionID, 
	NetVolumeMeasureType.unitCode, 
	NetVolumeMeasureType.unitCodeListVersionID, 
	NetWeightMeasureType.unitCode, 
	NetWeightMeasureType.unitCodeListVersionID, 
	NetworkIDType.schemeAgencyID, NetworkIDType.schemeAgencyName, 
	NetworkIDType.schemeDataURI, NetworkIDType.schemeID, 
	NetworkIDType.schemeName, NetworkIDType.schemeURI, 
	NetworkIDType.schemeVersionID, 
	NormalTemperatureReductionQuantityType.unitCode, 
	NormalTemperatureReductionQuantityType.unitCodeListAgencyID, 
	NormalTemperatureReductionQuantityType.unitCodeListAgencyName, 
	NormalTemperatureReductionQuantityType.unitCodeListID, 
	NoteType.languageID, NoteType.languageLocaleID, 
	NotificationTypeCodeType.languageID, 
	NotificationTypeCodeType.listAgencyID, 
	NotificationTypeCodeType.listAgencyName, 
	NotificationTypeCodeType.listID, NotificationTypeCodeType.listName, 
	NotificationTypeCodeType.listSchemeURI, 
	NotificationTypeCodeType.listURI, 
	NotificationTypeCodeType.listVersionID, NotificationTypeCodeType.name,
	OneTimeChargeTypeCodeType.languageID, 
	OneTimeChargeTypeCodeType.listAgencyID, 
	OneTimeChargeTypeCodeType.listAgencyName, 
	OneTimeChargeTypeCodeType.listID, OneTimeChargeTypeCodeType.listName, 
	OneTimeChargeTypeCodeType.listSchemeURI, 
	OneTimeChargeTypeCodeType.listURI, 
	OneTimeChargeTypeCodeType.listVersionID, 
	OneTimeChargeTypeCodeType.name, OneTimeChargeTypeType.languageID, 
	OneTimeChargeTypeType.languageLocaleID, 
	OntologyURIType.schemeAgencyID, OntologyURIType.schemeAgencyName, 
	OntologyURIType.schemeDataURI, OntologyURIType.schemeID, 
	OntologyURIType.schemeName, OntologyURIType.schemeURI, 
	OntologyURIType.schemeVersionID, OpenTenderIDType.schemeAgencyID, 
	OpenTenderIDType.schemeAgencyName, OpenTenderIDType.schemeDataURI, 
	OpenTenderIDType.schemeID, OpenTenderIDType.schemeName, 
	OpenTenderIDType.schemeURI, OpenTenderIDType.schemeVersionID, 
	OperatingYearsQuantityType.unitCode, 
	OperatingYearsQuantityType.unitCodeListAgencyID, 
	OperatingYearsQuantityType.unitCodeListAgencyName, 
	OperatingYearsQuantityType.unitCodeListID, 
	OperationStatusCodeType.languageID, 
	OperationStatusCodeType.listAgencyID, 
	OperationStatusCodeType.listAgencyName, 
	OperationStatusCodeType.listID, OperationStatusCodeType.listName, 
	OperationStatusCodeType.listSchemeURI, 
	OperationStatusCodeType.listURI, 
	OperationStatusCodeType.listVersionID, OperationStatusCodeType.name, 
	OptionsDescriptionType.languageID, 
	OptionsDescriptionType.languageLocaleID, 
	OrderIntervalDaysNumericType.format, 
	OrderQuantityIncrementNumericType.format, 
	OrderResponseCodeType.languageID, OrderResponseCodeType.listAgencyID, 
	OrderResponseCodeType.listAgencyName, OrderResponseCodeType.listID, 
	OrderResponseCodeType.listName, OrderResponseCodeType.listSchemeURI, 
	OrderResponseCodeType.listURI, OrderResponseCodeType.listVersionID, 
	OrderResponseCodeType.name, OrderTypeCodeType.languageID, 
	OrderTypeCodeType.listAgencyID, OrderTypeCodeType.listAgencyName, 
	OrderTypeCodeType.listID, OrderTypeCodeType.listName, 
	OrderTypeCodeType.listSchemeURI, OrderTypeCodeType.listURI, 
	OrderTypeCodeType.listVersionID, OrderTypeCodeType.name, 
	OrderableUnitFactorRateType.format, OrderableUnitType.languageID, 
	OrderableUnitType.languageLocaleID, 
	OrganizationDepartmentType.languageID, 
	OrganizationDepartmentType.languageLocaleID, 
	OriginalContractingSystemIDType.schemeAgencyID, 
	OriginalContractingSystemIDType.schemeAgencyName, 
	OriginalContractingSystemIDType.schemeDataURI, 
	OriginalContractingSystemIDType.schemeID, 
	OriginalContractingSystemIDType.schemeName, 
	OriginalContractingSystemIDType.schemeURI, 
	OriginalContractingSystemIDType.schemeVersionID, 
	OriginalJobIDType.schemeAgencyID, OriginalJobIDType.schemeAgencyName, 
	OriginalJobIDType.schemeDataURI, OriginalJobIDType.schemeID, 
	OriginalJobIDType.schemeName, OriginalJobIDType.schemeURI, 
	OriginalJobIDType.schemeVersionID, OtherInstructionType.languageID, 
	OtherInstructionType.languageLocaleID, 
	OutstandingQuantityType.unitCode, 
	OutstandingQuantityType.unitCodeListAgencyID, 
	OutstandingQuantityType.unitCodeListAgencyName, 
	OutstandingQuantityType.unitCodeListID, 
	OutstandingReasonType.languageID, 
	OutstandingReasonType.languageLocaleID, 
	OversupplyQuantityType.unitCode, 
	OversupplyQuantityType.unitCodeListAgencyID, 
	OversupplyQuantityType.unitCodeListAgencyName, 
	OversupplyQuantityType.unitCodeListID, OwnerTypeCodeType.languageID, 
	OwnerTypeCodeType.listAgencyID, OwnerTypeCodeType.listAgencyName, 
	OwnerTypeCodeType.listID, OwnerTypeCodeType.listName, 
	OwnerTypeCodeType.listSchemeURI, OwnerTypeCodeType.listURI, 
	OwnerTypeCodeType.listVersionID, OwnerTypeCodeType.name, 
	PackLevelCodeType.languageID, PackLevelCodeType.listAgencyID, 
	PackLevelCodeType.listAgencyName, PackLevelCodeType.listID, 
	PackLevelCodeType.listName, PackLevelCodeType.listSchemeURI, 
	PackLevelCodeType.listURI, PackLevelCodeType.listVersionID, 
	PackLevelCodeType.name, PackQuantityType.unitCode, 
	PackQuantityType.unitCodeListAgencyID, 
	PackQuantityType.unitCodeListAgencyName, 
	PackQuantityType.unitCodeListID, PackSizeNumericType.format, 
	PackageLevelCodeType.languageID, PackageLevelCodeType.listAgencyID, 
	PackageLevelCodeType.listAgencyName, PackageLevelCodeType.listID, 
	PackageLevelCodeType.listName, PackageLevelCodeType.listSchemeURI, 
	PackageLevelCodeType.listURI, PackageLevelCodeType.listVersionID, 
	PackageLevelCodeType.name, PackagingTypeCodeType.languageID, 
	PackagingTypeCodeType.listAgencyID, 
	PackagingTypeCodeType.listAgencyName, PackagingTypeCodeType.listID, 
	PackagingTypeCodeType.listName, PackagingTypeCodeType.listSchemeURI, 
	PackagingTypeCodeType.listURI, PackagingTypeCodeType.listVersionID, 
	PackagingTypeCodeType.name, PackingCriteriaCodeType.languageID, 
	PackingCriteriaCodeType.listAgencyID, 
	PackingCriteriaCodeType.listAgencyName, 
	PackingCriteriaCodeType.listID, PackingCriteriaCodeType.listName, 
	PackingCriteriaCodeType.listSchemeURI, 
	PackingCriteriaCodeType.listURI, 
	PackingCriteriaCodeType.listVersionID, PackingCriteriaCodeType.name, 
	PackingMaterialType.languageID, PackingMaterialType.languageLocaleID, 
	PaidAmountType.currencyCodeListVersionID, PaidAmountType.currencyID, 
	ParentDocumentIDType.schemeAgencyID, 
	ParentDocumentIDType.schemeAgencyName, 
	ParentDocumentIDType.schemeDataURI, ParentDocumentIDType.schemeID, 
	ParentDocumentIDType.schemeName, ParentDocumentIDType.schemeURI, 
	ParentDocumentIDType.schemeVersionID, 
	ParentDocumentLineReferenceIDType.schemeAgencyID, 
	ParentDocumentLineReferenceIDType.schemeAgencyName, 
	ParentDocumentLineReferenceIDType.schemeDataURI, 
	ParentDocumentLineReferenceIDType.schemeID, 
	ParentDocumentLineReferenceIDType.schemeName, 
	ParentDocumentLineReferenceIDType.schemeURI, 
	ParentDocumentLineReferenceIDType.schemeVersionID, 
	ParentDocumentTypeCodeType.languageID, 
	ParentDocumentTypeCodeType.listAgencyID, 
	ParentDocumentTypeCodeType.listAgencyName, 
	ParentDocumentTypeCodeType.listID, 
	ParentDocumentTypeCodeType.listName, 
	ParentDocumentTypeCodeType.listSchemeURI, 
	ParentDocumentTypeCodeType.listURI, 
	ParentDocumentTypeCodeType.listVersionID, 
	ParentDocumentTypeCodeType.name, 
	ParentDocumentVersionIDType.schemeAgencyID, 
	ParentDocumentVersionIDType.schemeAgencyName, 
	ParentDocumentVersionIDType.schemeDataURI, 
	ParentDocumentVersionIDType.schemeID, 
	ParentDocumentVersionIDType.schemeName, 
	ParentDocumentVersionIDType.schemeURI, 
	ParentDocumentVersionIDType.schemeVersionID, 
	PartPresentationCodeType.languageID, 
	PartPresentationCodeType.listAgencyID, 
	PartPresentationCodeType.listAgencyName, 
	PartPresentationCodeType.listID, PartPresentationCodeType.listName, 
	PartPresentationCodeType.listSchemeURI, 
	PartPresentationCodeType.listURI, 
	PartPresentationCodeType.listVersionID, PartPresentationCodeType.name,
	PartecipationPercentType.format, ParticipationPercentType.format, 
	PartyCapacityAmountType.currencyCodeListVersionID, 
	PartyCapacityAmountType.currencyID, PasswordType.languageID, 
	PasswordType.languageLocaleID, PayPerViewType.languageID, 
	PayPerViewType.languageLocaleID, 
	PayableAlternativeAmountType.currencyCodeListVersionID, 
	PayableAlternativeAmountType.currencyID, 
	PayableAmountType.currencyCodeListVersionID, 
	PayableAmountType.currencyID, 
	PayableRoundingAmountType.currencyCodeListVersionID, 
	PayableRoundingAmountType.currencyID, PayerReferenceType.languageID, 
	PayerReferenceType.languageLocaleID, 
	PaymentAlternativeCurrencyCodeType.languageID, 
	PaymentAlternativeCurrencyCodeType.listAgencyID, 
	PaymentAlternativeCurrencyCodeType.listAgencyName, 
	PaymentAlternativeCurrencyCodeType.listID, 
	PaymentAlternativeCurrencyCodeType.listName, 
	PaymentAlternativeCurrencyCodeType.listSchemeURI, 
	PaymentAlternativeCurrencyCodeType.listURI, 
	PaymentAlternativeCurrencyCodeType.listVersionID, 
	PaymentAlternativeCurrencyCodeType.name, 
	PaymentChannelCodeType.languageID, 
	PaymentChannelCodeType.listAgencyID, 
	PaymentChannelCodeType.listAgencyName, PaymentChannelCodeType.listID, 
	PaymentChannelCodeType.listName, PaymentChannelCodeType.listSchemeURI,
	PaymentChannelCodeType.listURI, PaymentChannelCodeType.listVersionID, 
	PaymentChannelCodeType.name, PaymentCurrencyCodeType.languageID, 
	PaymentCurrencyCodeType.listAgencyID, 
	PaymentCurrencyCodeType.listAgencyName, 
	PaymentCurrencyCodeType.listID, PaymentCurrencyCodeType.listName, 
	PaymentCurrencyCodeType.listSchemeURI, 
	PaymentCurrencyCodeType.listURI, 
	PaymentCurrencyCodeType.listVersionID, PaymentCurrencyCodeType.name, 
	PaymentFrequencyCodeType.languageID, 
	PaymentFrequencyCodeType.listAgencyID, 
	PaymentFrequencyCodeType.listAgencyName, 
	PaymentFrequencyCodeType.listID, PaymentFrequencyCodeType.listName, 
	PaymentFrequencyCodeType.listSchemeURI, 
	PaymentFrequencyCodeType.listURI, 
	PaymentFrequencyCodeType.listVersionID, PaymentFrequencyCodeType.name,
	PaymentIDType.schemeAgencyID, PaymentIDType.schemeAgencyName, 
	PaymentIDType.schemeDataURI, PaymentIDType.schemeID, 
	PaymentIDType.schemeName, PaymentIDType.schemeURI, 
	PaymentIDType.schemeVersionID, PaymentMeansCodeType.languageID, 
	PaymentMeansCodeType.listAgencyID, 
	PaymentMeansCodeType.listAgencyName, PaymentMeansCodeType.listID, 
	PaymentMeansCodeType.listName, PaymentMeansCodeType.listSchemeURI, 
	PaymentMeansCodeType.listURI, PaymentMeansCodeType.listVersionID, 
	PaymentMeansCodeType.name, PaymentMeansIDType.schemeAgencyID, 
	PaymentMeansIDType.schemeAgencyName, PaymentMeansIDType.schemeDataURI,
	PaymentMeansIDType.schemeID, PaymentMeansIDType.schemeName, 
	PaymentMeansIDType.schemeURI, PaymentMeansIDType.schemeVersionID, 
	PaymentNoteType.languageID, PaymentNoteType.languageLocaleID, 
	PaymentOrderReferenceType.languageID, 
	PaymentOrderReferenceType.languageLocaleID, PaymentPercentType.format,
	PaymentPurposeCodeType.languageID, 
	PaymentPurposeCodeType.listAgencyID, 
	PaymentPurposeCodeType.listAgencyName, PaymentPurposeCodeType.listID, 
	PaymentPurposeCodeType.listName, PaymentPurposeCodeType.listSchemeURI,
	PaymentPurposeCodeType.listURI, PaymentPurposeCodeType.listVersionID, 
	PaymentPurposeCodeType.name, 
	PaymentTermsDetailsURIType.schemeAgencyID, 
	PaymentTermsDetailsURIType.schemeAgencyName, 
	PaymentTermsDetailsURIType.schemeDataURI, 
	PaymentTermsDetailsURIType.schemeID, 
	PaymentTermsDetailsURIType.schemeName, 
	PaymentTermsDetailsURIType.schemeURI, 
	PaymentTermsDetailsURIType.schemeVersionID, 
	PenaltyAmountType.currencyCodeListVersionID, 
	PenaltyAmountType.currencyID, PenaltyClausesType.languageID, 
	PenaltyClausesType.languageLocaleID, 
	PenaltySurchargePercentType.format, 
	PerUnitAmountType.currencyCodeListVersionID, 
	PerUnitAmountType.currencyID, PercentType.format, 
	PerformanceMetricTypeCodeType.languageID, 
	PerformanceMetricTypeCodeType.listAgencyID, 
	PerformanceMetricTypeCodeType.listAgencyName, 
	PerformanceMetricTypeCodeType.listID, 
	PerformanceMetricTypeCodeType.listName, 
	PerformanceMetricTypeCodeType.listSchemeURI, 
	PerformanceMetricTypeCodeType.listURI, 
	PerformanceMetricTypeCodeType.listVersionID, 
	PerformanceMetricTypeCodeType.name, 
	PerformanceValueQuantityType.unitCode, 
	PerformanceValueQuantityType.unitCodeListAgencyID, 
	PerformanceValueQuantityType.unitCodeListAgencyName, 
	PerformanceValueQuantityType.unitCodeListID, 
	PerformingCarrierAssignedIDType.schemeAgencyID, 
	PerformingCarrierAssignedIDType.schemeAgencyName, 
	PerformingCarrierAssignedIDType.schemeDataURI, 
	PerformingCarrierAssignedIDType.schemeID, 
	PerformingCarrierAssignedIDType.schemeName, 
	PerformingCarrierAssignedIDType.schemeURI, 
	PerformingCarrierAssignedIDType.schemeVersionID, 
	PersonalSituationType.languageID, 
	PersonalSituationType.languageLocaleID, PhoneNumberType.languageID, 
	PhoneNumberType.languageLocaleID, PlacardEndorsementType.languageID, 
	PlacardEndorsementType.languageLocaleID, 
	PlacardNotationType.languageID, PlacardNotationType.languageLocaleID, 
	PlotIdentificationType.languageID, 
	PlotIdentificationType.languageLocaleID, PositionCodeType.languageID, 
	PositionCodeType.listAgencyID, PositionCodeType.listAgencyName, 
	PositionCodeType.listID, PositionCodeType.listName, 
	PositionCodeType.listSchemeURI, PositionCodeType.listURI, 
	PositionCodeType.listVersionID, PositionCodeType.name, 
	PostalZoneType.languageID, PostalZoneType.languageLocaleID, 
	PostboxType.languageID, PostboxType.languageLocaleID, 
	PreferenceCriterionCodeType.languageID, 
	PreferenceCriterionCodeType.listAgencyID, 
	PreferenceCriterionCodeType.listAgencyName, 
	PreferenceCriterionCodeType.listID, 
	PreferenceCriterionCodeType.listName, 
	PreferenceCriterionCodeType.listSchemeURI, 
	PreferenceCriterionCodeType.listURI, 
	PreferenceCriterionCodeType.listVersionID, 
	PreferenceCriterionCodeType.name, 
	PrepaidAmountType.currencyCodeListVersionID, 
	PrepaidAmountType.currencyID, 
	PrepaidPaymentReferenceIDType.schemeAgencyID, 
	PrepaidPaymentReferenceIDType.schemeAgencyName, 
	PrepaidPaymentReferenceIDType.schemeDataURI, 
	PrepaidPaymentReferenceIDType.schemeID, 
	PrepaidPaymentReferenceIDType.schemeName, 
	PrepaidPaymentReferenceIDType.schemeURI, 
	PrepaidPaymentReferenceIDType.schemeVersionID, 
	PreviousCancellationReasonCodeType.languageID, 
	PreviousCancellationReasonCodeType.listAgencyID, 
	PreviousCancellationReasonCodeType.listAgencyName, 
	PreviousCancellationReasonCodeType.listID, 
	PreviousCancellationReasonCodeType.listName, 
	PreviousCancellationReasonCodeType.listSchemeURI, 
	PreviousCancellationReasonCodeType.listURI, 
	PreviousCancellationReasonCodeType.listVersionID, 
	PreviousCancellationReasonCodeType.name, 
	PreviousJobIDType.schemeAgencyID, PreviousJobIDType.schemeAgencyName, 
	PreviousJobIDType.schemeDataURI, PreviousJobIDType.schemeID, 
	PreviousJobIDType.schemeName, PreviousJobIDType.schemeURI, 
	PreviousJobIDType.schemeVersionID, PreviousMeterQuantityType.unitCode,
	PreviousMeterQuantityType.unitCodeListAgencyID, 
	PreviousMeterQuantityType.unitCodeListAgencyName, 
	PreviousMeterQuantityType.unitCodeListID, 
	PreviousVersionIDType.schemeAgencyID, 
	PreviousVersionIDType.schemeAgencyName, 
	PreviousVersionIDType.schemeDataURI, PreviousVersionIDType.schemeID, 
	PreviousVersionIDType.schemeName, PreviousVersionIDType.schemeURI, 
	PreviousVersionIDType.schemeVersionID, 
	PriceAmountType.currencyCodeListVersionID, PriceAmountType.currencyID,
	PriceChangeReasonType.languageID, 
	PriceChangeReasonType.languageLocaleID, 
	PriceEvaluationCodeType.languageID, 
	PriceEvaluationCodeType.listAgencyID, 
	PriceEvaluationCodeType.listAgencyName, 
	PriceEvaluationCodeType.listID, PriceEvaluationCodeType.listName, 
	PriceEvaluationCodeType.listSchemeURI, 
	PriceEvaluationCodeType.listURI, 
	PriceEvaluationCodeType.listVersionID, PriceEvaluationCodeType.name, 
	PriceRevisionFormulaDescriptionType.languageID, 
	PriceRevisionFormulaDescriptionType.languageLocaleID, 
	PriceTypeCodeType.languageID, PriceTypeCodeType.listAgencyID, 
	PriceTypeCodeType.listAgencyName, PriceTypeCodeType.listID, 
	PriceTypeCodeType.listName, PriceTypeCodeType.listSchemeURI, 
	PriceTypeCodeType.listURI, PriceTypeCodeType.listVersionID, 
	PriceTypeCodeType.name, PriceTypeType.languageID, 
	PriceTypeType.languageLocaleID, PricingCurrencyCodeType.languageID, 
	PricingCurrencyCodeType.listAgencyID, 
	PricingCurrencyCodeType.listAgencyName, 
	PricingCurrencyCodeType.listID, PricingCurrencyCodeType.listName, 
	PricingCurrencyCodeType.listSchemeURI, 
	PricingCurrencyCodeType.listURI, 
	PricingCurrencyCodeType.listVersionID, PricingCurrencyCodeType.name, 
	PrimaryAccountNumberIDType.schemeAgencyID, 
	PrimaryAccountNumberIDType.schemeAgencyName, 
	PrimaryAccountNumberIDType.schemeDataURI, 
	PrimaryAccountNumberIDType.schemeID, 
	PrimaryAccountNumberIDType.schemeName, 
	PrimaryAccountNumberIDType.schemeURI, 
	PrimaryAccountNumberIDType.schemeVersionID, 
	PrintQualifierType.languageID, PrintQualifierType.languageLocaleID, 
	PriorityType.languageID, PriorityType.languageLocaleID, 
	PrivacyCodeType.languageID, PrivacyCodeType.listAgencyID, 
	PrivacyCodeType.listAgencyName, PrivacyCodeType.listID, 
	PrivacyCodeType.listName, PrivacyCodeType.listSchemeURI, 
	PrivacyCodeType.listURI, PrivacyCodeType.listVersionID, 
	PrivacyCodeType.name, ProcedureCodeType.languageID, 
	ProcedureCodeType.listAgencyID, ProcedureCodeType.listAgencyName, 
	ProcedureCodeType.listID, ProcedureCodeType.listName, 
	ProcedureCodeType.listSchemeURI, ProcedureCodeType.listURI, 
	ProcedureCodeType.listVersionID, ProcedureCodeType.name, 
	ProcessDescriptionType.languageID, 
	ProcessDescriptionType.languageLocaleID, 
	ProcessReasonCodeType.languageID, ProcessReasonCodeType.listAgencyID, 
	ProcessReasonCodeType.listAgencyName, ProcessReasonCodeType.listID, 
	ProcessReasonCodeType.listName, ProcessReasonCodeType.listSchemeURI, 
	ProcessReasonCodeType.listURI, ProcessReasonCodeType.listVersionID, 
	ProcessReasonCodeType.name, ProcessReasonType.languageID, 
	ProcessReasonType.languageLocaleID, 
	ProcurementProjectLotIDType.schemeAgencyID, 
	ProcurementProjectLotIDType.schemeAgencyName, 
	ProcurementProjectLotIDType.schemeDataURI, 
	ProcurementProjectLotIDType.schemeID, 
	ProcurementProjectLotIDType.schemeName, 
	ProcurementProjectLotIDType.schemeURI, 
	ProcurementProjectLotIDType.schemeVersionID, 
	ProcurementSubTypeCodeType.languageID, 
	ProcurementSubTypeCodeType.listAgencyID, 
	ProcurementSubTypeCodeType.listAgencyName, 
	ProcurementSubTypeCodeType.listID, 
	ProcurementSubTypeCodeType.listName, 
	ProcurementSubTypeCodeType.listSchemeURI, 
	ProcurementSubTypeCodeType.listURI, 
	ProcurementSubTypeCodeType.listVersionID, 
	ProcurementSubTypeCodeType.name, ProcurementTypeCodeType.languageID, 
	ProcurementTypeCodeType.listAgencyID, 
	ProcurementTypeCodeType.listAgencyName, 
	ProcurementTypeCodeType.listID, ProcurementTypeCodeType.listName, 
	ProcurementTypeCodeType.listSchemeURI, 
	ProcurementTypeCodeType.listURI, 
	ProcurementTypeCodeType.listVersionID, ProcurementTypeCodeType.name, 
	ProductTraceIDType.schemeAgencyID, 
	ProductTraceIDType.schemeAgencyName, ProductTraceIDType.schemeDataURI,
	ProductTraceIDType.schemeID, ProductTraceIDType.schemeName, 
	ProductTraceIDType.schemeURI, ProductTraceIDType.schemeVersionID, 
	ProfileExecutionIDType.schemeAgencyID, 
	ProfileExecutionIDType.schemeAgencyName, 
	ProfileExecutionIDType.schemeDataURI, ProfileExecutionIDType.schemeID,
	ProfileExecutionIDType.schemeName, ProfileExecutionIDType.schemeURI, 
	ProfileExecutionIDType.schemeVersionID, ProfileIDType.schemeAgencyID, 
	ProfileIDType.schemeAgencyName, ProfileIDType.schemeDataURI, 
	ProfileIDType.schemeID, ProfileIDType.schemeName, 
	ProfileIDType.schemeURI, ProfileIDType.schemeVersionID, 
	ProfileStatusCodeType.languageID, ProfileStatusCodeType.listAgencyID, 
	ProfileStatusCodeType.listAgencyName, ProfileStatusCodeType.listID, 
	ProfileStatusCodeType.listName, ProfileStatusCodeType.listSchemeURI, 
	ProfileStatusCodeType.listURI, ProfileStatusCodeType.listVersionID, 
	ProfileStatusCodeType.name, PromotionalEventTypeCodeType.languageID, 
	PromotionalEventTypeCodeType.listAgencyID, 
	PromotionalEventTypeCodeType.listAgencyName, 
	PromotionalEventTypeCodeType.listID, 
	PromotionalEventTypeCodeType.listName, 
	PromotionalEventTypeCodeType.listSchemeURI, 
	PromotionalEventTypeCodeType.listURI, 
	PromotionalEventTypeCodeType.listVersionID, 
	PromotionalEventTypeCodeType.name, ProviderTypeCodeType.languageID, 
	ProviderTypeCodeType.listAgencyID, 
	ProviderTypeCodeType.listAgencyName, ProviderTypeCodeType.listID, 
	ProviderTypeCodeType.listName, ProviderTypeCodeType.listSchemeURI, 
	ProviderTypeCodeType.listURI, ProviderTypeCodeType.listVersionID, 
	ProviderTypeCodeType.name, PurposeCodeType.languageID, 
	PurposeCodeType.listAgencyID, PurposeCodeType.listAgencyName, 
	PurposeCodeType.listID, PurposeCodeType.listName, 
	PurposeCodeType.listSchemeURI, PurposeCodeType.listURI, 
	PurposeCodeType.listVersionID, PurposeCodeType.name, 
	PurposeType.languageID, PurposeType.languageLocaleID, 
	QualityControlCodeType.languageID, 
	QualityControlCodeType.listAgencyID, 
	QualityControlCodeType.listAgencyName, QualityControlCodeType.listID, 
	QualityControlCodeType.listName, QualityControlCodeType.listSchemeURI,
	QualityControlCodeType.listURI, QualityControlCodeType.listVersionID, 
	QualityControlCodeType.name, QuantityDiscrepancyCodeType.languageID, 
	QuantityDiscrepancyCodeType.listAgencyID, 
	QuantityDiscrepancyCodeType.listAgencyName, 
	QuantityDiscrepancyCodeType.listID, 
	QuantityDiscrepancyCodeType.listName, 
	QuantityDiscrepancyCodeType.listSchemeURI, 
	QuantityDiscrepancyCodeType.listURI, 
	QuantityDiscrepancyCodeType.listVersionID, 
	QuantityDiscrepancyCodeType.name, QuantityType.unitCode, 
	QuantityType.unitCodeListAgencyID, 
	QuantityType.unitCodeListAgencyName, QuantityType.unitCodeListID, 
	RailCarIDType.schemeAgencyID, RailCarIDType.schemeAgencyName, 
	RailCarIDType.schemeDataURI, RailCarIDType.schemeID, 
	RailCarIDType.schemeName, RailCarIDType.schemeURI, 
	RailCarIDType.schemeVersionID, RateType.format, 
	ReceivedQuantityType.unitCode, 
	ReceivedQuantityType.unitCodeListAgencyID, 
	ReceivedQuantityType.unitCodeListAgencyName, 
	ReceivedQuantityType.unitCodeListID, 
	ReceivedTenderQuantityType.unitCode, 
	ReceivedTenderQuantityType.unitCodeListAgencyID, 
	ReceivedTenderQuantityType.unitCodeListAgencyName, 
	ReceivedTenderQuantityType.unitCodeListID, 
	ReferenceEventCodeType.languageID, 
	ReferenceEventCodeType.listAgencyID, 
	ReferenceEventCodeType.listAgencyName, ReferenceEventCodeType.listID, 
	ReferenceEventCodeType.listName, ReferenceEventCodeType.listSchemeURI,
	ReferenceEventCodeType.listURI, ReferenceEventCodeType.listVersionID, 
	ReferenceEventCodeType.name, ReferenceIDType.schemeAgencyID, 
	ReferenceIDType.schemeAgencyName, ReferenceIDType.schemeDataURI, 
	ReferenceIDType.schemeID, ReferenceIDType.schemeName, 
	ReferenceIDType.schemeURI, ReferenceIDType.schemeVersionID, 
	ReferenceType-1.languageID, ReferenceType-1.languageLocaleID, 
	ReferencedConsignmentIDType.schemeAgencyID, 
	ReferencedConsignmentIDType.schemeAgencyName, 
	ReferencedConsignmentIDType.schemeDataURI, 
	ReferencedConsignmentIDType.schemeID, 
	ReferencedConsignmentIDType.schemeName, 
	ReferencedConsignmentIDType.schemeURI, 
	ReferencedConsignmentIDType.schemeVersionID, RegionType.languageID, 
	RegionType.languageLocaleID, RegistrationIDType.schemeAgencyID, 
	RegistrationIDType.schemeAgencyName, RegistrationIDType.schemeDataURI,
	RegistrationIDType.schemeID, RegistrationIDType.schemeName, 
	RegistrationIDType.schemeURI, RegistrationIDType.schemeVersionID, 
	RegistrationNameType.languageID, 
	RegistrationNameType.languageLocaleID, 
	RegistrationNationalityIDType.schemeAgencyID, 
	RegistrationNationalityIDType.schemeAgencyName, 
	RegistrationNationalityIDType.schemeDataURI, 
	RegistrationNationalityIDType.schemeID, 
	RegistrationNationalityIDType.schemeName, 
	RegistrationNationalityIDType.schemeURI, 
	RegistrationNationalityIDType.schemeVersionID, 
	RegistrationNationalityType.languageID, 
	RegistrationNationalityType.languageLocaleID, 
	RejectActionCodeType.languageID, RejectActionCodeType.listAgencyID, 
	RejectActionCodeType.listAgencyName, RejectActionCodeType.listID, 
	RejectActionCodeType.listName, RejectActionCodeType.listSchemeURI, 
	RejectActionCodeType.listURI, RejectActionCodeType.listVersionID, 
	RejectActionCodeType.name, RejectReasonCodeType.languageID, 
	RejectReasonCodeType.listAgencyID, 
	RejectReasonCodeType.listAgencyName, RejectReasonCodeType.listID, 
	RejectReasonCodeType.listName, RejectReasonCodeType.listSchemeURI, 
	RejectReasonCodeType.listURI, RejectReasonCodeType.listVersionID, 
	RejectReasonCodeType.name, RejectReasonType.languageID, 
	RejectReasonType.languageLocaleID, RejectedQuantityType.unitCode, 
	RejectedQuantityType.unitCodeListAgencyID, 
	RejectedQuantityType.unitCodeListAgencyName, 
	RejectedQuantityType.unitCodeListID, RejectionNoteType.languageID, 
	RejectionNoteType.languageLocaleID, ReleaseIDType.schemeAgencyID, 
	ReleaseIDType.schemeAgencyName, ReleaseIDType.schemeDataURI, 
	ReleaseIDType.schemeID, ReleaseIDType.schemeName, 
	ReleaseIDType.schemeURI, ReleaseIDType.schemeVersionID, 
	ReliabilityPercentType.format, RemarksType.languageID, 
	RemarksType.languageLocaleID, ReminderSequenceNumericType.format, 
	ReminderTypeCodeType.languageID, ReminderTypeCodeType.listAgencyID, 
	ReminderTypeCodeType.listAgencyName, ReminderTypeCodeType.listID, 
	ReminderTypeCodeType.listName, ReminderTypeCodeType.listSchemeURI, 
	ReminderTypeCodeType.listURI, ReminderTypeCodeType.listVersionID, 
	ReminderTypeCodeType.name, 
	ReplenishmentOwnerDescriptionType.languageID, 
	ReplenishmentOwnerDescriptionType.languageLocaleID, 
	RequestForQuotationLineIDType.schemeAgencyID, 
	RequestForQuotationLineIDType.schemeAgencyName, 
	RequestForQuotationLineIDType.schemeDataURI, 
	RequestForQuotationLineIDType.schemeID, 
	RequestForQuotationLineIDType.schemeName, 
	RequestForQuotationLineIDType.schemeURI, 
	RequestForQuotationLineIDType.schemeVersionID, 
	RequestedInvoiceCurrencyCodeType.languageID, 
	RequestedInvoiceCurrencyCodeType.listAgencyID, 
	RequestedInvoiceCurrencyCodeType.listAgencyName, 
	RequestedInvoiceCurrencyCodeType.listID, 
	RequestedInvoiceCurrencyCodeType.listName, 
	RequestedInvoiceCurrencyCodeType.listSchemeURI, 
	RequestedInvoiceCurrencyCodeType.listURI, 
	RequestedInvoiceCurrencyCodeType.listVersionID, 
	RequestedInvoiceCurrencyCodeType.name, 
	RequiredCustomsIDType.schemeAgencyID, 
	RequiredCustomsIDType.schemeAgencyName, 
	RequiredCustomsIDType.schemeDataURI, RequiredCustomsIDType.schemeID, 
	RequiredCustomsIDType.schemeName, RequiredCustomsIDType.schemeURI, 
	RequiredCustomsIDType.schemeVersionID, 
	RequiredFeeAmountType.currencyCodeListVersionID, 
	RequiredFeeAmountType.currencyID, ResidenceTypeCodeType.languageID, 
	ResidenceTypeCodeType.listAgencyID, 
	ResidenceTypeCodeType.listAgencyName, ResidenceTypeCodeType.listID, 
	ResidenceTypeCodeType.listName, ResidenceTypeCodeType.listSchemeURI, 
	ResidenceTypeCodeType.listURI, ResidenceTypeCodeType.listVersionID, 
	ResidenceTypeCodeType.name, ResidenceTypeType.languageID, 
	ResidenceTypeType.languageLocaleID, 
	ResidentOccupantsNumericType.format, ResolutionCodeType.languageID, 
	ResolutionCodeType.listAgencyID, ResolutionCodeType.listAgencyName, 
	ResolutionCodeType.listID, ResolutionCodeType.listName, 
	ResolutionCodeType.listSchemeURI, ResolutionCodeType.listURI, 
	ResolutionCodeType.listVersionID, ResolutionCodeType.name, 
	ResolutionType.languageID, ResolutionType.languageLocaleID, 
	ResponseCodeType.languageID, ResponseCodeType.listAgencyID, 
	ResponseCodeType.listAgencyName, ResponseCodeType.listID, 
	ResponseCodeType.listName, ResponseCodeType.listSchemeURI, 
	ResponseCodeType.listURI, ResponseCodeType.listVersionID, 
	ResponseCodeType.name, RetailEventNameType.languageID, 
	RetailEventNameType.languageLocaleID, 
	RetailEventStatusCodeType.languageID, 
	RetailEventStatusCodeType.listAgencyID, 
	RetailEventStatusCodeType.listAgencyName, 
	RetailEventStatusCodeType.listID, RetailEventStatusCodeType.listName, 
	RetailEventStatusCodeType.listSchemeURI, 
	RetailEventStatusCodeType.listURI, 
	RetailEventStatusCodeType.listVersionID, 
	RetailEventStatusCodeType.name, ReturnableQuantityType.unitCode, 
	ReturnableQuantityType.unitCodeListAgencyID, 
	ReturnableQuantityType.unitCodeListAgencyName, 
	ReturnableQuantityType.unitCodeListID, 
	RevisedForecastLineIDType.schemeAgencyID, 
	RevisedForecastLineIDType.schemeAgencyName, 
	RevisedForecastLineIDType.schemeDataURI, 
	RevisedForecastLineIDType.schemeID, 
	RevisedForecastLineIDType.schemeName, 
	RevisedForecastLineIDType.schemeURI, 
	RevisedForecastLineIDType.schemeVersionID, 
	RevisionStatusCodeType.languageID, 
	RevisionStatusCodeType.listAgencyID, 
	RevisionStatusCodeType.listAgencyName, RevisionStatusCodeType.listID, 
	RevisionStatusCodeType.listName, RevisionStatusCodeType.listSchemeURI,
	RevisionStatusCodeType.listURI, RevisionStatusCodeType.listVersionID, 
	RevisionStatusCodeType.name, RoamingPartnerNameType.languageID, 
	RoamingPartnerNameType.languageLocaleID, RoleCodeType.languageID, 
	RoleCodeType.listAgencyID, RoleCodeType.listAgencyName, 
	RoleCodeType.listID, RoleCodeType.listName, 
	RoleCodeType.listSchemeURI, RoleCodeType.listURI, 
	RoleCodeType.listVersionID, RoleCodeType.name, RoomType.languageID, 
	RoomType.languageLocaleID, 
	RoundingAmountType.currencyCodeListVersionID, 
	RoundingAmountType.currencyID, SalesOrderIDType.schemeAgencyID, 
	SalesOrderIDType.schemeAgencyName, SalesOrderIDType.schemeDataURI, 
	SalesOrderIDType.schemeID, SalesOrderIDType.schemeName, 
	SalesOrderIDType.schemeURI, SalesOrderIDType.schemeVersionID, 
	SalesOrderLineIDType.schemeAgencyID, 
	SalesOrderLineIDType.schemeAgencyName, 
	SalesOrderLineIDType.schemeDataURI, SalesOrderLineIDType.schemeID, 
	SalesOrderLineIDType.schemeName, SalesOrderLineIDType.schemeURI, 
	SalesOrderLineIDType.schemeVersionID, SchemeURIType.schemeAgencyID, 
	SchemeURIType.schemeAgencyName, SchemeURIType.schemeDataURI, 
	SchemeURIType.schemeID, SchemeURIType.schemeName, 
	SchemeURIType.schemeURI, SchemeURIType.schemeVersionID, 
	SealIssuerTypeCodeType.languageID, 
	SealIssuerTypeCodeType.listAgencyID, 
	SealIssuerTypeCodeType.listAgencyName, SealIssuerTypeCodeType.listID, 
	SealIssuerTypeCodeType.listName, SealIssuerTypeCodeType.listSchemeURI,
	SealIssuerTypeCodeType.listURI, SealIssuerTypeCodeType.listVersionID, 
	SealIssuerTypeCodeType.name, SealStatusCodeType.languageID, 
	SealStatusCodeType.listAgencyID, SealStatusCodeType.listAgencyName, 
	SealStatusCodeType.listID, SealStatusCodeType.listName, 
	SealStatusCodeType.listSchemeURI, SealStatusCodeType.listURI, 
	SealStatusCodeType.listVersionID, SealStatusCodeType.name, 
	SealingPartyTypeType.languageID, 
	SealingPartyTypeType.languageLocaleID, 
	SecurityClassificationCodeType.languageID, 
	SecurityClassificationCodeType.listAgencyID, 
	SecurityClassificationCodeType.listAgencyName, 
	SecurityClassificationCodeType.listID, 
	SecurityClassificationCodeType.listName, 
	SecurityClassificationCodeType.listSchemeURI, 
	SecurityClassificationCodeType.listURI, 
	SecurityClassificationCodeType.listVersionID, 
	SecurityClassificationCodeType.name, SecurityIDType.schemeAgencyID, 
	SecurityIDType.schemeAgencyName, SecurityIDType.schemeDataURI, 
	SecurityIDType.schemeID, SecurityIDType.schemeName, 
	SecurityIDType.schemeURI, SecurityIDType.schemeVersionID, 
	SellerEventIDType.schemeAgencyID, SellerEventIDType.schemeAgencyName, 
	SellerEventIDType.schemeDataURI, SellerEventIDType.schemeID, 
	SellerEventIDType.schemeName, SellerEventIDType.schemeURI, 
	SellerEventIDType.schemeVersionID, SequenceIDType.schemeAgencyID, 
	SequenceIDType.schemeAgencyName, SequenceIDType.schemeDataURI, 
	SequenceIDType.schemeID, SequenceIDType.schemeName, 
	SequenceIDType.schemeURI, SequenceIDType.schemeVersionID, 
	SequenceNumberIDType.schemeAgencyID, 
	SequenceNumberIDType.schemeAgencyName, 
	SequenceNumberIDType.schemeDataURI, SequenceNumberIDType.schemeID, 
	SequenceNumberIDType.schemeName, SequenceNumberIDType.schemeURI, 
	SequenceNumberIDType.schemeVersionID, SequenceNumericType.format, 
	SerialIDType.schemeAgencyID, SerialIDType.schemeAgencyName, 
	SerialIDType.schemeDataURI, SerialIDType.schemeID, 
	SerialIDType.schemeName, SerialIDType.schemeURI, 
	SerialIDType.schemeVersionID, ServiceNameType.languageID, 
	ServiceNameType.languageLocaleID, ServiceNumberCalledType.languageID, 
	ServiceNumberCalledType.languageLocaleID, 
	ServiceTypeCodeType.languageID, ServiceTypeCodeType.listAgencyID, 
	ServiceTypeCodeType.listAgencyName, ServiceTypeCodeType.listID, 
	ServiceTypeCodeType.listName, ServiceTypeCodeType.listSchemeURI, 
	ServiceTypeCodeType.listURI, ServiceTypeCodeType.listVersionID, 
	ServiceTypeCodeType.name, ServiceTypeType.languageID, 
	ServiceTypeType.languageLocaleID, 
	SettlementDiscountAmountType.currencyCodeListVersionID, 
	SettlementDiscountAmountType.currencyID, 
	SettlementDiscountPercentType.format, 
	SharesNumberQuantityType.unitCode, 
	SharesNumberQuantityType.unitCodeListAgencyID, 
	SharesNumberQuantityType.unitCodeListAgencyName, 
	SharesNumberQuantityType.unitCodeListID, ShippingMarksType.languageID,
	ShippingMarksType.languageLocaleID, 
	ShippingOrderIDType.schemeAgencyID, 
	ShippingOrderIDType.schemeAgencyName, 
	ShippingOrderIDType.schemeDataURI, ShippingOrderIDType.schemeID, 
	ShippingOrderIDType.schemeName, ShippingOrderIDType.schemeURI, 
	ShippingOrderIDType.schemeVersionID, 
	ShippingPriorityLevelCodeType.languageID, 
	ShippingPriorityLevelCodeType.listAgencyID, 
	ShippingPriorityLevelCodeType.listAgencyName, 
	ShippingPriorityLevelCodeType.listID, 
	ShippingPriorityLevelCodeType.listName, 
	ShippingPriorityLevelCodeType.listSchemeURI, 
	ShippingPriorityLevelCodeType.listURI, 
	ShippingPriorityLevelCodeType.listVersionID, 
	ShippingPriorityLevelCodeType.name, ShortQuantityType.unitCode, 
	ShortQuantityType.unitCodeListAgencyID, 
	ShortQuantityType.unitCodeListAgencyName, 
	ShortQuantityType.unitCodeListID, ShortageActionCodeType.languageID, 
	ShortageActionCodeType.listAgencyID, 
	ShortageActionCodeType.listAgencyName, ShortageActionCodeType.listID, 
	ShortageActionCodeType.listName, ShortageActionCodeType.listSchemeURI,
	ShortageActionCodeType.listURI, ShortageActionCodeType.listVersionID, 
	ShortageActionCodeType.name, SignatureIDType.schemeAgencyID, 
	SignatureIDType.schemeAgencyName, SignatureIDType.schemeDataURI, 
	SignatureIDType.schemeID, SignatureIDType.schemeName, 
	SignatureIDType.schemeURI, SignatureIDType.schemeVersionID, 
	SignatureMethodType-1.languageID, 
	SignatureMethodType-1.languageLocaleID, SizeTypeCodeType.languageID, 
	SizeTypeCodeType.listAgencyID, SizeTypeCodeType.listAgencyName, 
	SizeTypeCodeType.listID, SizeTypeCodeType.listName, 
	SizeTypeCodeType.listSchemeURI, SizeTypeCodeType.listURI, 
	SizeTypeCodeType.listVersionID, SizeTypeCodeType.name, 
	SourceCurrencyBaseRateType.format, SourceCurrencyCodeType.languageID, 
	SourceCurrencyCodeType.listAgencyID, 
	SourceCurrencyCodeType.listAgencyName, SourceCurrencyCodeType.listID, 
	SourceCurrencyCodeType.listName, SourceCurrencyCodeType.listSchemeURI,
	SourceCurrencyCodeType.listURI, SourceCurrencyCodeType.listVersionID, 
	SourceCurrencyCodeType.name, SourceValueMeasureType.unitCode, 
	SourceValueMeasureType.unitCodeListVersionID, 
	SpecialInstructionsType.languageID, 
	SpecialInstructionsType.languageLocaleID, 
	SpecialServiceInstructionsType.languageID, 
	SpecialServiceInstructionsType.languageLocaleID, 
	SpecialTermsType.languageID, SpecialTermsType.languageLocaleID, 
	SpecialTransportRequirmentsType.languageID, 
	SpecialTransportRequirmentsType.languageLocaleID, 
	SpecificationIDType.schemeAgencyID, 
	SpecificationIDType.schemeAgencyName, 
	SpecificationIDType.schemeDataURI, SpecificationIDType.schemeID, 
	SpecificationIDType.schemeName, SpecificationIDType.schemeURI, 
	SpecificationIDType.schemeVersionID, 
	SpecificationTypeCodeType.languageID, 
	SpecificationTypeCodeType.listAgencyID, 
	SpecificationTypeCodeType.listAgencyName, 
	SpecificationTypeCodeType.listID, SpecificationTypeCodeType.listName, 
	SpecificationTypeCodeType.listSchemeURI, 
	SpecificationTypeCodeType.listURI, 
	SpecificationTypeCodeType.listVersionID, 
	SpecificationTypeCodeType.name, StatementTypeCodeType.languageID, 
	StatementTypeCodeType.listAgencyID, 
	StatementTypeCodeType.listAgencyName, StatementTypeCodeType.listID, 
	StatementTypeCodeType.listName, StatementTypeCodeType.listSchemeURI, 
	StatementTypeCodeType.listURI, StatementTypeCodeType.listVersionID, 
	StatementTypeCodeType.name, StatusCodeType.languageID, 
	StatusCodeType.listAgencyID, StatusCodeType.listAgencyName, 
	StatusCodeType.listID, StatusCodeType.listName, 
	StatusCodeType.listSchemeURI, StatusCodeType.listURI, 
	StatusCodeType.listVersionID, StatusCodeType.name, 
	StatusReasonCodeType.languageID, StatusReasonCodeType.listAgencyID, 
	StatusReasonCodeType.listAgencyName, StatusReasonCodeType.listID, 
	StatusReasonCodeType.listName, StatusReasonCodeType.listSchemeURI, 
	StatusReasonCodeType.listURI, StatusReasonCodeType.listVersionID, 
	StatusReasonCodeType.name, StatusReasonType.languageID, 
	StatusReasonType.languageLocaleID, StreetNameType.languageID, 
	StreetNameType.languageLocaleID, SubmissionMethodCodeType.languageID, 
	SubmissionMethodCodeType.listAgencyID, 
	SubmissionMethodCodeType.listAgencyName, 
	SubmissionMethodCodeType.listID, SubmissionMethodCodeType.listName, 
	SubmissionMethodCodeType.listSchemeURI, 
	SubmissionMethodCodeType.listURI, 
	SubmissionMethodCodeType.listVersionID, SubmissionMethodCodeType.name,
	SubscriberIDType-1.schemeAgencyID, 
	SubscriberIDType-1.schemeAgencyName, SubscriberIDType-1.schemeDataURI,
	SubscriberIDType-1.schemeID, SubscriberIDType-1.schemeName, 
	SubscriberIDType-1.schemeURI, SubscriberIDType-1.schemeVersionID, 
	SubscriberIDTypeCodeType.languageID, 
	SubscriberIDTypeCodeType.listAgencyID, 
	SubscriberIDTypeCodeType.listAgencyName, 
	SubscriberIDTypeCodeType.listID, SubscriberIDTypeCodeType.listName, 
	SubscriberIDTypeCodeType.listSchemeURI, 
	SubscriberIDTypeCodeType.listURI, 
	SubscriberIDTypeCodeType.listVersionID, SubscriberIDTypeCodeType.name,
	SubscriberIDTypeType.languageID, 
	SubscriberIDTypeType.languageLocaleID, 
	SubscriberTypeCodeType.languageID, 
	SubscriberTypeCodeType.listAgencyID, 
	SubscriberTypeCodeType.listAgencyName, SubscriberTypeCodeType.listID, 
	SubscriberTypeCodeType.listName, SubscriberTypeCodeType.listSchemeURI,
	SubscriberTypeCodeType.listURI, SubscriberTypeCodeType.listVersionID, 
	SubscriberTypeCodeType.name, SubscriberTypeIdentifierType.languageID, 
	SubscriberTypeIdentifierType.languageLocaleID, 
	SubstitutionStatusCodeType.languageID, 
	SubstitutionStatusCodeType.listAgencyID, 
	SubstitutionStatusCodeType.listAgencyName, 
	SubstitutionStatusCodeType.listID, 
	SubstitutionStatusCodeType.listName, 
	SubstitutionStatusCodeType.listSchemeURI, 
	SubstitutionStatusCodeType.listURI, 
	SubstitutionStatusCodeType.listVersionID, 
	SubstitutionStatusCodeType.name, 
	SuccessiveSequenceIDType.schemeAgencyID, 
	SuccessiveSequenceIDType.schemeAgencyName, 
	SuccessiveSequenceIDType.schemeDataURI, 
	SuccessiveSequenceIDType.schemeID, 
	SuccessiveSequenceIDType.schemeName, 
	SuccessiveSequenceIDType.schemeURI, 
	SuccessiveSequenceIDType.schemeVersionID, 
	SummaryDescriptionType.languageID, 
	SummaryDescriptionType.languageLocaleID, 
	SupplierAssignedAccountIDType.schemeAgencyID, 
	SupplierAssignedAccountIDType.schemeAgencyName, 
	SupplierAssignedAccountIDType.schemeDataURI, 
	SupplierAssignedAccountIDType.schemeID, 
	SupplierAssignedAccountIDType.schemeName, 
	SupplierAssignedAccountIDType.schemeURI, 
	SupplierAssignedAccountIDType.schemeVersionID, 
	SupplyChainActivityTypeCodeType.languageID, 
	SupplyChainActivityTypeCodeType.listAgencyID, 
	SupplyChainActivityTypeCodeType.listAgencyName, 
	SupplyChainActivityTypeCodeType.listID, 
	SupplyChainActivityTypeCodeType.listName, 
	SupplyChainActivityTypeCodeType.listSchemeURI, 
	SupplyChainActivityTypeCodeType.listURI, 
	SupplyChainActivityTypeCodeType.listVersionID, 
	SupplyChainActivityTypeCodeType.name, TareWeightMeasureType.unitCode, 
	TareWeightMeasureType.unitCodeListVersionID, 
	TargetCurrencyBaseRateType.format, TargetCurrencyCodeType.languageID, 
	TargetCurrencyCodeType.listAgencyID, 
	TargetCurrencyCodeType.listAgencyName, TargetCurrencyCodeType.listID, 
	TargetCurrencyCodeType.listName, TargetCurrencyCodeType.listSchemeURI,
	TargetCurrencyCodeType.listURI, TargetCurrencyCodeType.listVersionID, 
	TargetCurrencyCodeType.name, TargetInventoryQuantityType.unitCode, 
	TargetInventoryQuantityType.unitCodeListAgencyID, 
	TargetInventoryQuantityType.unitCodeListAgencyName, 
	TargetInventoryQuantityType.unitCodeListID, 
	TargetServicePercentType.format, TariffClassCodeType.languageID, 
	TariffClassCodeType.listAgencyID, TariffClassCodeType.listAgencyName, 
	TariffClassCodeType.listID, TariffClassCodeType.listName, 
	TariffClassCodeType.listSchemeURI, TariffClassCodeType.listURI, 
	TariffClassCodeType.listVersionID, TariffClassCodeType.name, 
	TariffCodeType.languageID, TariffCodeType.listAgencyID, 
	TariffCodeType.listAgencyName, TariffCodeType.listID, 
	TariffCodeType.listName, TariffCodeType.listSchemeURI, 
	TariffCodeType.listURI, TariffCodeType.listVersionID, 
	TariffCodeType.name, TariffDescriptionType.languageID, 
	TariffDescriptionType.languageLocaleID, 
	TaxAmountType.currencyCodeListVersionID, TaxAmountType.currencyID, 
	TaxCurrencyCodeType.languageID, TaxCurrencyCodeType.listAgencyID, 
	TaxCurrencyCodeType.listAgencyName, TaxCurrencyCodeType.listID, 
	TaxCurrencyCodeType.listName, TaxCurrencyCodeType.listSchemeURI, 
	TaxCurrencyCodeType.listURI, TaxCurrencyCodeType.listVersionID, 
	TaxCurrencyCodeType.name, 
	TaxEnergyAmountType.currencyCodeListVersionID, 
	TaxEnergyAmountType.currencyID, 
	TaxEnergyBalanceAmountType.currencyCodeListVersionID, 
	TaxEnergyBalanceAmountType.currencyID, 
	TaxEnergyOnAccountAmountType.currencyCodeListVersionID, 
	TaxEnergyOnAccountAmountType.currencyID, 
	TaxExclusiveAmountType.currencyCodeListVersionID, 
	TaxExclusiveAmountType.currencyID, 
	TaxExemptionReasonCodeType.languageID, 
	TaxExemptionReasonCodeType.listAgencyID, 
	TaxExemptionReasonCodeType.listAgencyName, 
	TaxExemptionReasonCodeType.listID, 
	TaxExemptionReasonCodeType.listName, 
	TaxExemptionReasonCodeType.listSchemeURI, 
	TaxExemptionReasonCodeType.listURI, 
	TaxExemptionReasonCodeType.listVersionID, 
	TaxExemptionReasonCodeType.name, TaxExemptionReasonType.languageID, 
	TaxExemptionReasonType.languageLocaleID, 
	TaxInclusiveAmountType.currencyCodeListVersionID, 
	TaxInclusiveAmountType.currencyID, TaxLevelCodeType.languageID, 
	TaxLevelCodeType.listAgencyID, TaxLevelCodeType.listAgencyName, 
	TaxLevelCodeType.listID, TaxLevelCodeType.listName, 
	TaxLevelCodeType.listSchemeURI, TaxLevelCodeType.listURI, 
	TaxLevelCodeType.listVersionID, TaxLevelCodeType.name, 
	TaxTypeCodeType.languageID, TaxTypeCodeType.listAgencyID, 
	TaxTypeCodeType.listAgencyName, TaxTypeCodeType.listID, 
	TaxTypeCodeType.listName, TaxTypeCodeType.listSchemeURI, 
	TaxTypeCodeType.listURI, TaxTypeCodeType.listVersionID, 
	TaxTypeCodeType.name, TaxableAmountType.currencyCodeListVersionID, 
	TaxableAmountType.currencyID, 
	TechnicalCommitteeDescriptionType.languageID, 
	TechnicalCommitteeDescriptionType.languageLocaleID, 
	TechnicalNameType.languageID, TechnicalNameType.languageLocaleID, 
	TelecommunicationsServiceCallCodeType.languageID, 
	TelecommunicationsServiceCallCodeType.listAgencyID, 
	TelecommunicationsServiceCallCodeType.listAgencyName, 
	TelecommunicationsServiceCallCodeType.listID, 
	TelecommunicationsServiceCallCodeType.listName, 
	TelecommunicationsServiceCallCodeType.listSchemeURI, 
	TelecommunicationsServiceCallCodeType.listURI, 
	TelecommunicationsServiceCallCodeType.listVersionID, 
	TelecommunicationsServiceCallCodeType.name, 
	TelecommunicationsServiceCallType.languageID, 
	TelecommunicationsServiceCallType.languageLocaleID, 
	TelecommunicationsServiceCategoryCodeType.languageID, 
	TelecommunicationsServiceCategoryCodeType.listAgencyID, 
	TelecommunicationsServiceCategoryCodeType.listAgencyName, 
	TelecommunicationsServiceCategoryCodeType.listID, 
	TelecommunicationsServiceCategoryCodeType.listName, 
	TelecommunicationsServiceCategoryCodeType.listSchemeURI, 
	TelecommunicationsServiceCategoryCodeType.listURI, 
	TelecommunicationsServiceCategoryCodeType.listVersionID, 
	TelecommunicationsServiceCategoryCodeType.name, 
	TelecommunicationsServiceCategoryType.languageID, 
	TelecommunicationsServiceCategoryType.languageLocaleID, 
	TelecommunicationsSupplyTypeCodeType.languageID, 
	TelecommunicationsSupplyTypeCodeType.listAgencyID, 
	TelecommunicationsSupplyTypeCodeType.listAgencyName, 
	TelecommunicationsSupplyTypeCodeType.listID, 
	TelecommunicationsSupplyTypeCodeType.listName, 
	TelecommunicationsSupplyTypeCodeType.listSchemeURI, 
	TelecommunicationsSupplyTypeCodeType.listURI, 
	TelecommunicationsSupplyTypeCodeType.listVersionID, 
	TelecommunicationsSupplyTypeCodeType.name, 
	TelecommunicationsSupplyTypeType.languageID, 
	TelecommunicationsSupplyTypeType.languageLocaleID, 
	TelefaxType.languageID, TelefaxType.languageLocaleID, 
	TelephoneType.languageID, TelephoneType.languageLocaleID, 
	TenderEnvelopeIDType.schemeAgencyID, 
	TenderEnvelopeIDType.schemeAgencyName, 
	TenderEnvelopeIDType.schemeDataURI, TenderEnvelopeIDType.schemeID, 
	TenderEnvelopeIDType.schemeName, TenderEnvelopeIDType.schemeURI, 
	TenderEnvelopeIDType.schemeVersionID, 
	TenderEnvelopeTypeCodeType.languageID, 
	TenderEnvelopeTypeCodeType.listAgencyID, 
	TenderEnvelopeTypeCodeType.listAgencyName, 
	TenderEnvelopeTypeCodeType.listID, 
	TenderEnvelopeTypeCodeType.listName, 
	TenderEnvelopeTypeCodeType.listSchemeURI, 
	TenderEnvelopeTypeCodeType.listURI, 
	TenderEnvelopeTypeCodeType.listVersionID, 
	TenderEnvelopeTypeCodeType.name, TenderResultCodeType.languageID, 
	TenderResultCodeType.listAgencyID, 
	TenderResultCodeType.listAgencyName, TenderResultCodeType.listID, 
	TenderResultCodeType.listName, TenderResultCodeType.listSchemeURI, 
	TenderResultCodeType.listURI, TenderResultCodeType.listVersionID, 
	TenderResultCodeType.name, TenderTypeCodeType.languageID, 
	TenderTypeCodeType.listAgencyID, TenderTypeCodeType.listAgencyName, 
	TenderTypeCodeType.listID, TenderTypeCodeType.listName, 
	TenderTypeCodeType.listSchemeURI, TenderTypeCodeType.listURI, 
	TenderTypeCodeType.listVersionID, TenderTypeCodeType.name, 
	TendererRequirementTypeCodeType.languageID, 
	TendererRequirementTypeCodeType.listAgencyID, 
	TendererRequirementTypeCodeType.listAgencyName, 
	TendererRequirementTypeCodeType.listID, 
	TendererRequirementTypeCodeType.listName, 
	TendererRequirementTypeCodeType.listSchemeURI, 
	TendererRequirementTypeCodeType.listURI, 
	TendererRequirementTypeCodeType.listVersionID, 
	TendererRequirementTypeCodeType.name, TestMethodType.languageID, 
	TestMethodType.languageLocaleID, TextType.languageID, 
	TextType.languageLocaleID, 
	ThresholdAmountType.currencyCodeListVersionID, 
	ThresholdAmountType.currencyID, ThresholdQuantityType.unitCode, 
	ThresholdQuantityType.unitCodeListAgencyID, 
	ThresholdQuantityType.unitCodeListAgencyName, 
	ThresholdQuantityType.unitCodeListID, 
	ThresholdValueComparisonCodeType.languageID, 
	ThresholdValueComparisonCodeType.listAgencyID, 
	ThresholdValueComparisonCodeType.listAgencyName, 
	ThresholdValueComparisonCodeType.listID, 
	ThresholdValueComparisonCodeType.listName, 
	ThresholdValueComparisonCodeType.listSchemeURI, 
	ThresholdValueComparisonCodeType.listURI, 
	ThresholdValueComparisonCodeType.listVersionID, 
	ThresholdValueComparisonCodeType.name, TierRangeType.languageID, 
	TierRangeType.languageLocaleID, TierRatePercentType.format, 
	TimeAmountType.languageID, TimeAmountType.languageLocaleID, 
	TimeDeltaDaysQuantityType.unitCode, 
	TimeDeltaDaysQuantityType.unitCodeListAgencyID, 
	TimeDeltaDaysQuantityType.unitCodeListAgencyName, 
	TimeDeltaDaysQuantityType.unitCodeListID, 
	TimeFrequencyCodeType.languageID, TimeFrequencyCodeType.listAgencyID, 
	TimeFrequencyCodeType.listAgencyName, TimeFrequencyCodeType.listID, 
	TimeFrequencyCodeType.listName, TimeFrequencyCodeType.listSchemeURI, 
	TimeFrequencyCodeType.listURI, TimeFrequencyCodeType.listVersionID, 
	TimeFrequencyCodeType.name, TimezoneOffsetType.languageID, 
	TimezoneOffsetType.languageLocaleID, 
	TimingComplaintCodeType.languageID, 
	TimingComplaintCodeType.listAgencyID, 
	TimingComplaintCodeType.listAgencyName, 
	TimingComplaintCodeType.listID, TimingComplaintCodeType.listName, 
	TimingComplaintCodeType.listSchemeURI, 
	TimingComplaintCodeType.listURI, 
	TimingComplaintCodeType.listVersionID, TimingComplaintCodeType.name, 
	TimingComplaintType.languageID, TimingComplaintType.languageLocaleID, 
	TitleType.languageID, TitleType.languageLocaleID, 
	TotalAmountType.currencyCodeListVersionID, TotalAmountType.currencyID,
	TotalBalanceAmountType.currencyCodeListVersionID, 
	TotalBalanceAmountType.currencyID, TotalConsumedQuantityType.unitCode,
	TotalConsumedQuantityType.unitCodeListAgencyID, 
	TotalConsumedQuantityType.unitCodeListAgencyName, 
	TotalConsumedQuantityType.unitCodeListID, 
	TotalCreditAmountType.currencyCodeListVersionID, 
	TotalCreditAmountType.currencyID, 
	TotalDebitAmountType.currencyCodeListVersionID, 
	TotalDebitAmountType.currencyID, TotalDeliveredQuantityType.unitCode, 
	TotalDeliveredQuantityType.unitCodeListAgencyID, 
	TotalDeliveredQuantityType.unitCodeListAgencyName, 
	TotalDeliveredQuantityType.unitCodeListID, 
	TotalGoodsItemQuantityType.unitCode, 
	TotalGoodsItemQuantityType.unitCodeListAgencyID, 
	TotalGoodsItemQuantityType.unitCodeListAgencyName, 
	TotalGoodsItemQuantityType.unitCodeListID, 
	TotalInvoiceAmountType.currencyCodeListVersionID, 
	TotalInvoiceAmountType.currencyID, TotalMeteredQuantityType.unitCode, 
	TotalMeteredQuantityType.unitCodeListAgencyID, 
	TotalMeteredQuantityType.unitCodeListAgencyName, 
	TotalMeteredQuantityType.unitCodeListID, 
	TotalPackageQuantityType.unitCode, 
	TotalPackageQuantityType.unitCodeListAgencyID, 
	TotalPackageQuantityType.unitCodeListAgencyName, 
	TotalPackageQuantityType.unitCodeListID, 
	TotalPackagesQuantityType.unitCode, 
	TotalPackagesQuantityType.unitCodeListAgencyID, 
	TotalPackagesQuantityType.unitCodeListAgencyName, 
	TotalPackagesQuantityType.unitCodeListID, 
	TotalPaymentAmountType.currencyCodeListVersionID, 
	TotalPaymentAmountType.currencyID, 
	TotalTaskAmountType.currencyCodeListVersionID, 
	TotalTaskAmountType.currencyID, 
	TotalTaxAmountType.currencyCodeListVersionID, 
	TotalTaxAmountType.currencyID, 
	TotalTransportHandlingUnitQuantityType.unitCode, 
	TotalTransportHandlingUnitQuantityType.unitCodeListAgencyID, 
	TotalTransportHandlingUnitQuantityType.unitCodeListAgencyName, 
	TotalTransportHandlingUnitQuantityType.unitCodeListID, 
	TraceIDType.schemeAgencyID, TraceIDType.schemeAgencyName, 
	TraceIDType.schemeDataURI, TraceIDType.schemeID, 
	TraceIDType.schemeName, TraceIDType.schemeURI, 
	TraceIDType.schemeVersionID, TrackingDeviceCodeType.languageID, 
	TrackingDeviceCodeType.listAgencyID, 
	TrackingDeviceCodeType.listAgencyName, TrackingDeviceCodeType.listID, 
	TrackingDeviceCodeType.listName, TrackingDeviceCodeType.listSchemeURI,
	TrackingDeviceCodeType.listURI, TrackingDeviceCodeType.listVersionID, 
	TrackingDeviceCodeType.name, TrackingIDType.schemeAgencyID, 
	TrackingIDType.schemeAgencyName, TrackingIDType.schemeDataURI, 
	TrackingIDType.schemeID, TrackingIDType.schemeName, 
	TrackingIDType.schemeURI, TrackingIDType.schemeVersionID, 
	TradeItemPackingLabelingTypeCodeType.languageID, 
	TradeItemPackingLabelingTypeCodeType.listAgencyID, 
	TradeItemPackingLabelingTypeCodeType.listAgencyName, 
	TradeItemPackingLabelingTypeCodeType.listID, 
	TradeItemPackingLabelingTypeCodeType.listName, 
	TradeItemPackingLabelingTypeCodeType.listSchemeURI, 
	TradeItemPackingLabelingTypeCodeType.listURI, 
	TradeItemPackingLabelingTypeCodeType.listVersionID, 
	TradeItemPackingLabelingTypeCodeType.name, 
	TradeServiceCodeType.languageID, TradeServiceCodeType.listAgencyID, 
	TradeServiceCodeType.listAgencyName, TradeServiceCodeType.listID, 
	TradeServiceCodeType.listName, TradeServiceCodeType.listSchemeURI, 
	TradeServiceCodeType.listURI, TradeServiceCodeType.listVersionID, 
	TradeServiceCodeType.name, TradingRestrictionsType.languageID, 
	TradingRestrictionsType.languageLocaleID, TrainIDType.schemeAgencyID, 
	TrainIDType.schemeAgencyName, TrainIDType.schemeDataURI, 
	TrainIDType.schemeID, TrainIDType.schemeName, TrainIDType.schemeURI, 
	TrainIDType.schemeVersionID, 
	TransactionCurrencyTaxAmountType.currencyCodeListVersionID, 
	TransactionCurrencyTaxAmountType.currencyID, 
	TransitDirectionCodeType.languageID, 
	TransitDirectionCodeType.listAgencyID, 
	TransitDirectionCodeType.listAgencyName, 
	TransitDirectionCodeType.listID, TransitDirectionCodeType.listName, 
	TransitDirectionCodeType.listSchemeURI, 
	TransitDirectionCodeType.listURI, 
	TransitDirectionCodeType.listVersionID, TransitDirectionCodeType.name,
	TransportAuthorizationCodeType.languageID, 
	TransportAuthorizationCodeType.listAgencyID, 
	TransportAuthorizationCodeType.listAgencyName, 
	TransportAuthorizationCodeType.listID, 
	TransportAuthorizationCodeType.listName, 
	TransportAuthorizationCodeType.listSchemeURI, 
	TransportAuthorizationCodeType.listURI, 
	TransportAuthorizationCodeType.listVersionID, 
	TransportAuthorizationCodeType.name, 
	TransportEmergencyCardCodeType.languageID, 
	TransportEmergencyCardCodeType.listAgencyID, 
	TransportEmergencyCardCodeType.listAgencyName, 
	TransportEmergencyCardCodeType.listID, 
	TransportEmergencyCardCodeType.listName, 
	TransportEmergencyCardCodeType.listSchemeURI, 
	TransportEmergencyCardCodeType.listURI, 
	TransportEmergencyCardCodeType.listVersionID, 
	TransportEmergencyCardCodeType.name, 
	TransportEquipmentTypeCodeType.languageID, 
	TransportEquipmentTypeCodeType.listAgencyID, 
	TransportEquipmentTypeCodeType.listAgencyName, 
	TransportEquipmentTypeCodeType.listID, 
	TransportEquipmentTypeCodeType.listName, 
	TransportEquipmentTypeCodeType.listSchemeURI, 
	TransportEquipmentTypeCodeType.listURI, 
	TransportEquipmentTypeCodeType.listVersionID, 
	TransportEquipmentTypeCodeType.name, 
	TransportEventTypeCodeType.languageID, 
	TransportEventTypeCodeType.listAgencyID, 
	TransportEventTypeCodeType.listAgencyName, 
	TransportEventTypeCodeType.listID, 
	TransportEventTypeCodeType.listName, 
	TransportEventTypeCodeType.listSchemeURI, 
	TransportEventTypeCodeType.listURI, 
	TransportEventTypeCodeType.listVersionID, 
	TransportEventTypeCodeType.name, 
	TransportExecutionPlanReferenceIDType.schemeAgencyID, 
	TransportExecutionPlanReferenceIDType.schemeAgencyName, 
	TransportExecutionPlanReferenceIDType.schemeDataURI, 
	TransportExecutionPlanReferenceIDType.schemeID, 
	TransportExecutionPlanReferenceIDType.schemeName, 
	TransportExecutionPlanReferenceIDType.schemeURI, 
	TransportExecutionPlanReferenceIDType.schemeVersionID, 
	TransportHandlingUnitTypeCodeType.languageID, 
	TransportHandlingUnitTypeCodeType.listAgencyID, 
	TransportHandlingUnitTypeCodeType.listAgencyName, 
	TransportHandlingUnitTypeCodeType.listID, 
	TransportHandlingUnitTypeCodeType.listName, 
	TransportHandlingUnitTypeCodeType.listSchemeURI, 
	TransportHandlingUnitTypeCodeType.listURI, 
	TransportHandlingUnitTypeCodeType.listVersionID, 
	TransportHandlingUnitTypeCodeType.name, 
	TransportMeansTypeCodeType.languageID, 
	TransportMeansTypeCodeType.listAgencyID, 
	TransportMeansTypeCodeType.listAgencyName, 
	TransportMeansTypeCodeType.listID, 
	TransportMeansTypeCodeType.listName, 
	TransportMeansTypeCodeType.listSchemeURI, 
	TransportMeansTypeCodeType.listURI, 
	TransportMeansTypeCodeType.listVersionID, 
	TransportMeansTypeCodeType.name, TransportModeCodeType.languageID, 
	TransportModeCodeType.listAgencyID, 
	TransportModeCodeType.listAgencyName, TransportModeCodeType.listID, 
	TransportModeCodeType.listName, TransportModeCodeType.listSchemeURI, 
	TransportModeCodeType.listURI, TransportModeCodeType.listVersionID, 
	TransportModeCodeType.name, TransportServiceCodeType.languageID, 
	TransportServiceCodeType.listAgencyID, 
	TransportServiceCodeType.listAgencyName, 
	TransportServiceCodeType.listID, TransportServiceCodeType.listName, 
	TransportServiceCodeType.listSchemeURI, 
	TransportServiceCodeType.listURI, 
	TransportServiceCodeType.listVersionID, TransportServiceCodeType.name,
	TransportServiceProviderRemarksType.languageID, 
	TransportServiceProviderRemarksType.languageLocaleID, 
	TransportServiceProviderSpecialTermsType.languageID, 
	TransportServiceProviderSpecialTermsType.languageLocaleID, 
	TransportUserRemarksType.languageID, 
	TransportUserRemarksType.languageLocaleID, 
	TransportUserSpecialTermsType.languageID, 
	TransportUserSpecialTermsType.languageLocaleID, 
	TransportationServiceDescriptionType.languageID, 
	TransportationServiceDescriptionType.languageLocaleID, 
	TransportationServiceDetailsURIType.schemeAgencyID, 
	TransportationServiceDetailsURIType.schemeAgencyName, 
	TransportationServiceDetailsURIType.schemeDataURI, 
	TransportationServiceDetailsURIType.schemeID, 
	TransportationServiceDetailsURIType.schemeName, 
	TransportationServiceDetailsURIType.schemeURI, 
	TransportationServiceDetailsURIType.schemeVersionID, 
	TypeCodeType.languageID, TypeCodeType.listAgencyID, 
	TypeCodeType.listAgencyName, TypeCodeType.listID, 
	TypeCodeType.listName, TypeCodeType.listSchemeURI, 
	TypeCodeType.listURI, TypeCodeType.listVersionID, TypeCodeType.name, 
	UBLVersionIDType.schemeAgencyID, UBLVersionIDType.schemeAgencyName, 
	UBLVersionIDType.schemeDataURI, UBLVersionIDType.schemeID, 
	UBLVersionIDType.schemeName, UBLVersionIDType.schemeURI, 
	UBLVersionIDType.schemeVersionID, UNDGCodeType.languageID, 
	UNDGCodeType.listAgencyID, UNDGCodeType.listAgencyName, 
	UNDGCodeType.listID, UNDGCodeType.listName, 
	UNDGCodeType.listSchemeURI, UNDGCodeType.listURI, 
	UNDGCodeType.listVersionID, UNDGCodeType.name, URIType.schemeAgencyID,
	URIType.schemeAgencyName, URIType.schemeDataURI, URIType.schemeID, 
	URIType.schemeName, URIType.schemeURI, URIType.schemeVersionID, 
	UUIDType.schemeAgencyID, UUIDType.schemeAgencyName, 
	UUIDType.schemeDataURI, UUIDType.schemeID, UUIDType.schemeName, 
	UUIDType.schemeURI, UUIDType.schemeVersionID, 
	UpperOrangeHazardPlacardIDType.schemeAgencyID, 
	UpperOrangeHazardPlacardIDType.schemeAgencyName, 
	UpperOrangeHazardPlacardIDType.schemeDataURI, 
	UpperOrangeHazardPlacardIDType.schemeID, 
	UpperOrangeHazardPlacardIDType.schemeName, 
	UpperOrangeHazardPlacardIDType.schemeURI, 
	UpperOrangeHazardPlacardIDType.schemeVersionID, 
	UrgencyCodeType.languageID, UrgencyCodeType.listAgencyID, 
	UrgencyCodeType.listAgencyName, UrgencyCodeType.listID, 
	UrgencyCodeType.listName, UrgencyCodeType.listSchemeURI, 
	UrgencyCodeType.listURI, UrgencyCodeType.listVersionID, 
	UrgencyCodeType.name, UtilityStatementTypeCodeType.languageID, 
	UtilityStatementTypeCodeType.listAgencyID, 
	UtilityStatementTypeCodeType.listAgencyName, 
	UtilityStatementTypeCodeType.listID, 
	UtilityStatementTypeCodeType.listName, 
	UtilityStatementTypeCodeType.listSchemeURI, 
	UtilityStatementTypeCodeType.listURI, 
	UtilityStatementTypeCodeType.listVersionID, 
	UtilityStatementTypeCodeType.name, ValidateProcessType.languageID, 
	ValidateProcessType.languageLocaleID, ValidateToolType.languageID, 
	ValidateToolType.languageLocaleID, ValidateToolVersionType.languageID,
	ValidateToolVersionType.languageLocaleID, 
	ValidationResultCodeType.languageID, 
	ValidationResultCodeType.listAgencyID, 
	ValidationResultCodeType.listAgencyName, 
	ValidationResultCodeType.listID, ValidationResultCodeType.listName, 
	ValidationResultCodeType.listSchemeURI, 
	ValidationResultCodeType.listURI, 
	ValidationResultCodeType.listVersionID, ValidationResultCodeType.name,
	ValidatorIDType.schemeAgencyID, ValidatorIDType.schemeAgencyName, 
	ValidatorIDType.schemeDataURI, ValidatorIDType.schemeID, 
	ValidatorIDType.schemeName, ValidatorIDType.schemeURI, 
	ValidatorIDType.schemeVersionID, 
	ValueAmountType.currencyCodeListVersionID, ValueAmountType.currencyID,
	ValueMeasureType.unitCode, ValueMeasureType.unitCodeListVersionID, 
	ValueQualifierType.languageID, ValueQualifierType.languageLocaleID, 
	ValueQuantityType.unitCode, ValueQuantityType.unitCodeListAgencyID, 
	ValueQuantityType.unitCodeListAgencyName, 
	ValueQuantityType.unitCodeListID, ValueType.languageID, 
	ValueType.languageLocaleID, VarianceQuantityType.unitCode, 
	VarianceQuantityType.unitCodeListAgencyID, 
	VarianceQuantityType.unitCodeListAgencyName, 
	VarianceQuantityType.unitCodeListID, VariantIDType.schemeAgencyID, 
	VariantIDType.schemeAgencyName, VariantIDType.schemeDataURI, 
	VariantIDType.schemeID, VariantIDType.schemeName, 
	VariantIDType.schemeURI, VariantIDType.schemeVersionID, 
	VersionIDType.schemeAgencyID, VersionIDType.schemeAgencyName, 
	VersionIDType.schemeDataURI, VersionIDType.schemeID, 
	VersionIDType.schemeName, VersionIDType.schemeURI, 
	VersionIDType.schemeVersionID, VesselIDType.schemeAgencyID, 
	VesselIDType.schemeAgencyName, VesselIDType.schemeDataURI, 
	VesselIDType.schemeID, VesselIDType.schemeName, 
	VesselIDType.schemeURI, VesselIDType.schemeVersionID, 
	VesselNameType.languageID, VesselNameType.languageLocaleID, 
	WarrantyInformationType.languageID, 
	WarrantyInformationType.languageLocaleID, 
	WebsiteURIType.schemeAgencyID, WebsiteURIType.schemeAgencyName, 
	WebsiteURIType.schemeDataURI, WebsiteURIType.schemeID, 
	WebsiteURIType.schemeName, WebsiteURIType.schemeURI, 
	WebsiteURIType.schemeVersionID, WeightNumericType.format, 
	WeightType.languageID, WeightType.languageLocaleID, 
	WeightingAlgorithmCodeType.languageID, 
	WeightingAlgorithmCodeType.listAgencyID, 
	WeightingAlgorithmCodeType.listAgencyName, 
	WeightingAlgorithmCodeType.listID, 
	WeightingAlgorithmCodeType.listName, 
	WeightingAlgorithmCodeType.listSchemeURI, 
	WeightingAlgorithmCodeType.listURI, 
	WeightingAlgorithmCodeType.listVersionID, 
	WeightingAlgorithmCodeType.name, XPathType.languageID, 
	XPathType.languageLocaleID
    NAME CanonicalizationMethod-1 AS "CanonicalizationMethod"
    NAME CertificateType-1 AS "CertificateType"
    NAME ConsumptionType-1 AS "ConsumptionType"
    NAME ContractType-1 AS "ContractType"
    NAME CorrectionType-1 AS "CorrectionType"
    NAME Date-1 AS "Date"
    NAME Duty-1 AS "Duty"
    NAME ID-1 AS "ID"
    NAME Location-1 AS "Location"
    NAME MeterReadingType-1 AS "MeterReadingType"
    NAME Name-1 AS "Name"
    NAME PriceType-1 AS "PriceType"
    NAME Reference-1 AS "Reference"
    NAME SignatureMethod-1 AS "SignatureMethod"
    NAME TelecommunicationsSupplyType-1 AS "TelecommunicationsSupplyType"
    NAME CanonicalizationMethodType-1 AS "CanonicalizationMethodType"
    NAME DutyType-1 AS "DutyType"
    NAME LocationType-1 AS "LocationType"
    NAME ReferenceType-1 AS "ReferenceType"
    NAME SignatureMethodType-1 AS "SignatureMethodType"
    NAME SubscriberIDType-1 AS "SubscriberIDType"
    ATTRIBUTE AcceptedVariantsDescriptionType.languageID, 
	AcceptedVariantsDescriptionType.languageLocaleID, 
	AccountingCostType.languageID, AccountingCostType.languageLocaleID, 
	AdditionalInformationType.languageID, 
	AdditionalInformationType.languageLocaleID, 
	AdditionalStreetNameType.languageID, 
	AdditionalStreetNameType.languageLocaleID, 
	AdvertisementAmountType.currencyCodeListVersionID, 
	AdvertisementAmountType.currencyID, AgencyNameType.languageID, 
	AgencyNameType.languageLocaleID, AirFlowPercentType.format, 
	AliasNameType.languageID, AliasNameType.languageLocaleID, 
	AllowanceChargeReasonType.languageID, 
	AllowanceChargeReasonType.languageLocaleID, 
	AllowanceTotalAmountType.currencyCodeListVersionID, 
	AllowanceTotalAmountType.currencyID, AltitudeMeasureType.unitCode, 
	AltitudeMeasureType.unitCodeListVersionID, AmountRateType.format, 
	AmountType.currencyCodeListVersionID, AmountType.currencyID, 
	AnnualAverageAmountType.currencyCodeListVersionID, 
	AnnualAverageAmountType.currencyID, ApprovalStatusType.languageID, 
	ApprovalStatusType.languageLocaleID, 
	AverageAmountType.currencyCodeListVersionID, 
	AverageAmountType.currencyID, 
	AverageSubsequentContractAmountType.currencyCodeListVersionID, 
	AverageSubsequentContractAmountType.currencyID, 
	AwardingCriteriaDescriptionType.languageID, 
	AwardingCriteriaDescriptionType.languageLocaleID, 
	BackorderReasonType.languageID, BackorderReasonType.languageLocaleID, 
	BalanceAmountType.currencyCodeListVersionID, 
	BalanceAmountType.currencyID, 
	BaseAmountType.currencyCodeListVersionID, BaseAmountType.currencyID, 
	BaseUnitMeasureType.unitCode, 
	BaseUnitMeasureType.unitCodeListVersionID, BlockNameType.languageID, 
	BlockNameType.languageLocaleID, BrandNameType.languageID, 
	BrandNameType.languageLocaleID, BudgetYearNumericType.format, 
	BuildingNameType.languageID, BuildingNameType.languageLocaleID, 
	BuildingNumberType.languageID, BuildingNumberType.languageLocaleID, 
	CalculationExpressionType.languageID, 
	CalculationExpressionType.languageLocaleID, 
	CalculationRateType.format, CalculationSequenceNumericType.format, 
	CallBaseAmountType.currencyCodeListVersionID, 
	CallBaseAmountType.currencyID, 
	CallExtensionAmountType.currencyCodeListVersionID, 
	CallExtensionAmountType.currencyID, CancellationNoteType.languageID, 
	CancellationNoteType.languageLocaleID, 
	CanonicalizationMethodType-1.languageID, 
	CanonicalizationMethodType-1.languageLocaleID, 
	CarrierServiceInstructionsType.languageID, 
	CarrierServiceInstructionsType.languageLocaleID, 
	CategoryNameType.languageID, CategoryNameType.languageLocaleID, 
	CertificateTypeType.languageID, CertificateTypeType.languageLocaleID, 
	ChangeConditionsType.languageID, 
	ChangeConditionsType.languageLocaleID, ChannelType.languageID, 
	ChannelType.languageLocaleID, CharacteristicsType.languageID, 
	CharacteristicsType.languageLocaleID, 
	ChargeTotalAmountType.currencyCodeListVersionID, 
	ChargeTotalAmountType.currencyID, 
	ChargeableWeightMeasureType.unitCode, 
	ChargeableWeightMeasureType.unitCodeListVersionID, 
	CityNameType.languageID, CityNameType.languageLocaleID, 
	CitySubdivisionNameType.languageID, 
	CitySubdivisionNameType.languageLocaleID, ClauseType.languageID, 
	ClauseType.languageLocaleID, CodeValueType.languageID, 
	CodeValueType.languageLocaleID, CommentType.languageID, 
	CommentType.languageLocaleID, ComparedValueMeasureType.unitCode, 
	ComparedValueMeasureType.unitCodeListVersionID, 
	ConditionType.languageID, ConditionType.languageLocaleID, 
	ConditionValueMeasureType.unitCode, 
	ConditionValueMeasureType.unitCodeListVersionID, 
	ConditionsDescriptionType.languageID, 
	ConditionsDescriptionType.languageLocaleID, ConditionsType.languageID,
	ConditionsType.languageLocaleID, ConsumersEnergyLevelType.languageID, 
	ConsumersEnergyLevelType.languageLocaleID, 
	ConsumptionLevelType.languageID, 
	ConsumptionLevelType.languageLocaleID, ConsumptionTypeType.languageID,
	ConsumptionTypeType.languageLocaleID, ContractNameType.languageID, 
	ContractNameType.languageLocaleID, ContractSubdivisionType.languageID,
	ContractSubdivisionType.languageLocaleID, ContractTypeType.languageID,
	ContractTypeType.languageLocaleID, 
	CorporateStockAmountType.currencyCodeListVersionID, 
	CorporateStockAmountType.currencyID, 
	CorrectionAmountType.currencyCodeListVersionID, 
	CorrectionAmountType.currencyID, CorrectionTypeType.languageID, 
	CorrectionTypeType.languageLocaleID, 
	CorrectionUnitAmountType.currencyCodeListVersionID, 
	CorrectionUnitAmountType.currencyID, CountrySubentityType.languageID, 
	CountrySubentityType.languageLocaleID, 
	CreditLineAmountType.currencyCodeListVersionID, 
	CreditLineAmountType.currencyID, CurrentChargeTypeType.languageID, 
	CurrentChargeTypeType.languageLocaleID, 
	CustomerReferenceType.languageID, 
	CustomerReferenceType.languageLocaleID, 
	CustomsClearanceServiceInstructionsType.languageID, 
	CustomsClearanceServiceInstructionsType.languageLocaleID, 
	DamageRemarksType.languageID, DamageRemarksType.languageLocaleID, 
	DataSendingCapabilityType.languageID, 
	DataSendingCapabilityType.languageLocaleID, 
	DebitLineAmountType.currencyCodeListVersionID, 
	DebitLineAmountType.currencyID, 
	DeclaredCarriageValueAmountType.currencyCodeListVersionID, 
	DeclaredCarriageValueAmountType.currencyID, 
	DeclaredCustomsValueAmountType.currencyCodeListVersionID, 
	DeclaredCustomsValueAmountType.currencyID, 
	DeclaredForCarriageValueAmountType.currencyCodeListVersionID, 
	DeclaredForCarriageValueAmountType.currencyID, 
	DeclaredStatisticsValueAmountType.currencyCodeListVersionID, 
	DeclaredStatisticsValueAmountType.currencyID, 
	DeliveryInstructionsType.languageID, 
	DeliveryInstructionsType.languageLocaleID, 
	DemurrageInstructionsType.languageID, 
	DemurrageInstructionsType.languageLocaleID, DepartmentType.languageID,
	DepartmentType.languageLocaleID, DescriptionType.languageID, 
	DescriptionType.languageLocaleID, DistrictType.languageID, 
	DistrictType.languageLocaleID, DocumentDescriptionType.languageID, 
	DocumentDescriptionType.languageLocaleID, DocumentHashType.languageID,
	DocumentHashType.languageLocaleID, DocumentTypeType.languageID, 
	DocumentTypeType.languageLocaleID, DurationMeasureType.unitCode, 
	DurationMeasureType.unitCodeListVersionID, DutyType-1.languageID, 
	DutyType-1.languageLocaleID, 
	ElectronicDeviceDescriptionType.languageID, 
	ElectronicDeviceDescriptionType.languageLocaleID, 
	ElectronicMailType.languageID, ElectronicMailType.languageLocaleID, 
	EstimatedOverallContractAmountType.currencyCodeListVersionID, 
	EstimatedOverallContractAmountType.currencyID, 
	ExclusionReasonType.languageID, ExclusionReasonType.languageLocaleID, 
	ExemptionReasonType.languageID, ExemptionReasonType.languageLocaleID, 
	ExtensionType.languageID, ExtensionType.languageLocaleID, 
	FaceValueAmountType.currencyCodeListVersionID, 
	FaceValueAmountType.currencyID, FamilyNameType.languageID, 
	FamilyNameType.languageLocaleID, 
	FeeAmountType.currencyCodeListVersionID, FeeAmountType.currencyID, 
	FeeDescriptionType.languageID, FeeDescriptionType.languageLocaleID, 
	FileNameType.languageID, FileNameType.languageLocaleID, 
	FirstNameType.languageID, FirstNameType.languageLocaleID, 
	FloorType.languageID, FloorType.languageLocaleID, 
	ForwarderServiceInstructionsType.languageID, 
	ForwarderServiceInstructionsType.languageLocaleID, 
	FreeOnBoardValueAmountType.currencyCodeListVersionID, 
	FreeOnBoardValueAmountType.currencyID, FrequencyType.languageID, 
	FrequencyType.languageLocaleID, FrozenPeriodDaysNumericType.format, 
	FundingProgramType.languageID, FundingProgramType.languageLocaleID, 
	GrossVolumeMeasureType.unitCode, 
	GrossVolumeMeasureType.unitCodeListVersionID, 
	GrossWeightMeasureType.unitCode, 
	GrossWeightMeasureType.unitCodeListVersionID, 
	HandlingInstructionsType.languageID, 
	HandlingInstructionsType.languageLocaleID, 
	HashAlgorithmMethodType.languageID, 
	HashAlgorithmMethodType.languageLocaleID, 
	HaulageInstructionsType.languageID, 
	HaulageInstructionsType.languageLocaleID, HeatingTypeType.languageID, 
	HeatingTypeType.languageLocaleID, 
	HigherTenderAmountType.currencyCodeListVersionID, 
	HigherTenderAmountType.currencyID, HolderNameType.languageID, 
	HolderNameType.languageLocaleID, HumidityPercentType.format, 
	InformationType.languageID, InformationType.languageLocaleID, 
	InhouseMailType.languageID, InhouseMailType.languageLocaleID, 
	InstructionNoteType.languageID, InstructionNoteType.languageLocaleID, 
	InstructionsType.languageID, InstructionsType.languageLocaleID, 
	InsurancePremiumAmountType.currencyCodeListVersionID, 
	InsurancePremiumAmountType.currencyID, 
	InsuranceValueAmountType.currencyCodeListVersionID, 
	InsuranceValueAmountType.currencyID, 
	InventoryValueAmountType.currencyCodeListVersionID, 
	InventoryValueAmountType.currencyID, 
	InvoicingPartyReferenceType.languageID, 
	InvoicingPartyReferenceType.languageLocaleID, JobTitleType.languageID,
	JobTitleType.languageLocaleID, 
	JustificationDescriptionType.languageID, 
	JustificationDescriptionType.languageLocaleID, 
	JustificationType.languageID, JustificationType.languageLocaleID, 
	KeywordType.languageID, KeywordType.languageLocaleID, 
	LatitudeDegreesMeasureType.unitCode, 
	LatitudeDegreesMeasureType.unitCodeListVersionID, 
	LatitudeMinutesMeasureType.unitCode, 
	LatitudeMinutesMeasureType.unitCodeListVersionID, 
	LeadTimeMeasureType.unitCode, 
	LeadTimeMeasureType.unitCodeListVersionID, LegalFormType.languageID, 
	LegalFormType.languageLocaleID, LegalReferenceType.languageID, 
	LegalReferenceType.languageLocaleID, 
	LiabilityAmountType.currencyCodeListVersionID, 
	LiabilityAmountType.currencyID, LimitationDescriptionType.languageID, 
	LimitationDescriptionType.languageLocaleID, 
	LineCountNumericType.format, 
	LineExtensionAmountType.currencyCodeListVersionID, 
	LineExtensionAmountType.currencyID, LineNumberNumericType.format, 
	LineType.languageID, LineType.languageLocaleID, 
	ListValueType.languageID, ListValueType.languageLocaleID, 
	LoadingLengthMeasureType.unitCode, 
	LoadingLengthMeasureType.unitCodeListVersionID, 
	LocationType-1.languageID, LocationType-1.languageLocaleID, 
	LoginType.languageID, LoginType.languageLocaleID, 
	LongitudeDegreesMeasureType.unitCode, 
	LongitudeDegreesMeasureType.unitCodeListVersionID, 
	LongitudeMinutesMeasureType.unitCode, 
	LongitudeMinutesMeasureType.unitCodeListVersionID, 
	LossRiskType.languageID, LossRiskType.languageLocaleID, 
	LowTendersDescriptionType.languageID, 
	LowTendersDescriptionType.languageLocaleID, 
	LowerTenderAmountType.currencyCodeListVersionID, 
	LowerTenderAmountType.currencyID, MarkAttentionType.languageID, 
	MarkAttentionType.languageLocaleID, MarkCareType.languageID, 
	MarkCareType.languageLocaleID, 
	MarketValueAmountType.currencyCodeListVersionID, 
	MarketValueAmountType.currencyID, 
	MaximumAdvertisementAmountType.currencyCodeListVersionID, 
	MaximumAdvertisementAmountType.currencyID, 
	MaximumAmountType.currencyCodeListVersionID, 
	MaximumAmountType.currencyID, MaximumCopiesNumericType.format, 
	MaximumMeasureType.unitCode, MaximumMeasureType.unitCodeListVersionID,
	MaximumNumberNumericType.format, 
	MaximumPaidAmountType.currencyCodeListVersionID, 
	MaximumPaidAmountType.currencyID, 
	MaximumPaymentInstructionsNumericType.format, 
	MaximumTaxExclusiveAmountType.currencyCodeListVersionID, 
	MaximumTaxExclusiveAmountType.currencyID, 
	MaximumTaxInclusiveAmountType.currencyCodeListVersionID, 
	MaximumTaxInclusiveAmountType.currencyID, MaximumValueType.languageID,
	MaximumValueType.languageLocaleID, MeasureType.unitCode, 
	MeasureType.unitCodeListVersionID, MeterConstantType.languageID, 
	MeterConstantType.languageLocaleID, MeterNameType.languageID, 
	MeterNameType.languageLocaleID, MeterNumberType.languageID, 
	MeterNumberType.languageLocaleID, MeterReadingCommentsType.languageID,
	MeterReadingCommentsType.languageLocaleID, 
	MeterReadingMethodType.languageID, 
	MeterReadingMethodType.languageLocaleID, 
	MeterReadingTypeType.languageID, 
	MeterReadingTypeType.languageLocaleID, MiddleNameType.languageID, 
	MiddleNameType.languageLocaleID, 
	MinimumAmountType.currencyCodeListVersionID, 
	MinimumAmountType.currencyID, MinimumImprovementBidType.languageID, 
	MinimumImprovementBidType.languageLocaleID, 
	MinimumMeasureType.unitCode, MinimumMeasureType.unitCodeListVersionID,
	MinimumNumberNumericType.format, MinimumValueType.languageID, 
	MinimumValueType.languageLocaleID, ModelNameType.languageID, 
	ModelNameType.languageLocaleID, MonetaryScopeType.languageID, 
	MonetaryScopeType.languageLocaleID, MovieTitleType.languageID, 
	MovieTitleType.languageLocaleID, MultiplierFactorNumericType.format, 
	NameSuffixType.languageID, NameSuffixType.languageLocaleID, 
	NameType.languageID, NameType.languageLocaleID, 
	NegotiationDescriptionType.languageID, 
	NegotiationDescriptionType.languageLocaleID, 
	NetNetWeightMeasureType.unitCode, 
	NetNetWeightMeasureType.unitCodeListVersionID, 
	NetVolumeMeasureType.unitCode, 
	NetVolumeMeasureType.unitCodeListVersionID, 
	NetWeightMeasureType.unitCode, 
	NetWeightMeasureType.unitCodeListVersionID, NoteType.languageID, 
	NoteType.languageLocaleID, OneTimeChargeTypeType.languageID, 
	OneTimeChargeTypeType.languageLocaleID, 
	OptionsDescriptionType.languageID, 
	OptionsDescriptionType.languageLocaleID, 
	OrderIntervalDaysNumericType.format, 
	OrderQuantityIncrementNumericType.format, 
	OrderableUnitFactorRateType.format, OrderableUnitType.languageID, 
	OrderableUnitType.languageLocaleID, 
	OrganizationDepartmentType.languageID, 
	OrganizationDepartmentType.languageLocaleID, 
	OtherInstructionType.languageID, 
	OtherInstructionType.languageLocaleID, 
	OutstandingReasonType.languageID, 
	OutstandingReasonType.languageLocaleID, PackSizeNumericType.format, 
	PackingMaterialType.languageID, PackingMaterialType.languageLocaleID, 
	PaidAmountType.currencyCodeListVersionID, PaidAmountType.currencyID, 
	PartecipationPercentType.format, ParticipationPercentType.format, 
	PartyCapacityAmountType.currencyCodeListVersionID, 
	PartyCapacityAmountType.currencyID, PasswordType.languageID, 
	PasswordType.languageLocaleID, PayPerViewType.languageID, 
	PayPerViewType.languageLocaleID, 
	PayableAlternativeAmountType.currencyCodeListVersionID, 
	PayableAlternativeAmountType.currencyID, 
	PayableAmountType.currencyCodeListVersionID, 
	PayableAmountType.currencyID, 
	PayableRoundingAmountType.currencyCodeListVersionID, 
	PayableRoundingAmountType.currencyID, PayerReferenceType.languageID, 
	PayerReferenceType.languageLocaleID, PaymentNoteType.languageID, 
	PaymentNoteType.languageLocaleID, 
	PaymentOrderReferenceType.languageID, 
	PaymentOrderReferenceType.languageLocaleID, PaymentPercentType.format,
	PenaltyAmountType.currencyCodeListVersionID, 
	PenaltyAmountType.currencyID, PenaltyClausesType.languageID, 
	PenaltyClausesType.languageLocaleID, 
	PenaltySurchargePercentType.format, 
	PerUnitAmountType.currencyCodeListVersionID, 
	PerUnitAmountType.currencyID, PercentType.format, 
	PersonalSituationType.languageID, 
	PersonalSituationType.languageLocaleID, PhoneNumberType.languageID, 
	PhoneNumberType.languageLocaleID, PlacardEndorsementType.languageID, 
	PlacardEndorsementType.languageLocaleID, 
	PlacardNotationType.languageID, PlacardNotationType.languageLocaleID, 
	PlotIdentificationType.languageID, 
	PlotIdentificationType.languageLocaleID, PostalZoneType.languageID, 
	PostalZoneType.languageLocaleID, PostboxType.languageID, 
	PostboxType.languageLocaleID, 
	PrepaidAmountType.currencyCodeListVersionID, 
	PrepaidAmountType.currencyID, 
	PriceAmountType.currencyCodeListVersionID, PriceAmountType.currencyID,
	PriceChangeReasonType.languageID, 
	PriceChangeReasonType.languageLocaleID, 
	PriceRevisionFormulaDescriptionType.languageID, 
	PriceRevisionFormulaDescriptionType.languageLocaleID, 
	PriceTypeType.languageID, PriceTypeType.languageLocaleID, 
	PrintQualifierType.languageID, PrintQualifierType.languageLocaleID, 
	PriorityType.languageID, PriorityType.languageLocaleID, 
	ProcessDescriptionType.languageID, 
	ProcessDescriptionType.languageLocaleID, ProcessReasonType.languageID,
	ProcessReasonType.languageLocaleID, PurposeType.languageID, 
	PurposeType.languageLocaleID, RateType.format, 
	ReferenceType-1.languageID, ReferenceType-1.languageLocaleID, 
	RegionType.languageID, RegionType.languageLocaleID, 
	RegistrationNameType.languageID, 
	RegistrationNameType.languageLocaleID, 
	RegistrationNationalityType.languageID, 
	RegistrationNationalityType.languageLocaleID, 
	RejectReasonType.languageID, RejectReasonType.languageLocaleID, 
	RejectionNoteType.languageID, RejectionNoteType.languageLocaleID, 
	ReliabilityPercentType.format, RemarksType.languageID, 
	RemarksType.languageLocaleID, ReminderSequenceNumericType.format, 
	ReplenishmentOwnerDescriptionType.languageID, 
	ReplenishmentOwnerDescriptionType.languageLocaleID, 
	RequiredFeeAmountType.currencyCodeListVersionID, 
	RequiredFeeAmountType.currencyID, ResidenceTypeType.languageID, 
	ResidenceTypeType.languageLocaleID, 
	ResidentOccupantsNumericType.format, ResolutionType.languageID, 
	ResolutionType.languageLocaleID, RetailEventNameType.languageID, 
	RetailEventNameType.languageLocaleID, 
	RoamingPartnerNameType.languageID, 
	RoamingPartnerNameType.languageLocaleID, RoomType.languageID, 
	RoomType.languageLocaleID, 
	RoundingAmountType.currencyCodeListVersionID, 
	RoundingAmountType.currencyID, SealingPartyTypeType.languageID, 
	SealingPartyTypeType.languageLocaleID, SequenceNumericType.format, 
	ServiceNameType.languageID, ServiceNameType.languageLocaleID, 
	ServiceNumberCalledType.languageID, 
	ServiceNumberCalledType.languageLocaleID, ServiceTypeType.languageID, 
	ServiceTypeType.languageLocaleID, 
	SettlementDiscountAmountType.currencyCodeListVersionID, 
	SettlementDiscountAmountType.currencyID, 
	SettlementDiscountPercentType.format, ShippingMarksType.languageID, 
	ShippingMarksType.languageLocaleID, SignatureMethodType-1.languageID, 
	SignatureMethodType-1.languageLocaleID, 
	SourceCurrencyBaseRateType.format, SourceValueMeasureType.unitCode, 
	SourceValueMeasureType.unitCodeListVersionID, 
	SpecialInstructionsType.languageID, 
	SpecialInstructionsType.languageLocaleID, 
	SpecialServiceInstructionsType.languageID, 
	SpecialServiceInstructionsType.languageLocaleID, 
	SpecialTermsType.languageID, SpecialTermsType.languageLocaleID, 
	SpecialTransportRequirmentsType.languageID, 
	SpecialTransportRequirmentsType.languageLocaleID, 
	StatusReasonType.languageID, StatusReasonType.languageLocaleID, 
	StreetNameType.languageID, StreetNameType.languageLocaleID, 
	SubscriberIDTypeType.languageID, 
	SubscriberIDTypeType.languageLocaleID, 
	SubscriberTypeIdentifierType.languageID, 
	SubscriberTypeIdentifierType.languageLocaleID, 
	SummaryDescriptionType.languageID, 
	SummaryDescriptionType.languageLocaleID, 
	TareWeightMeasureType.unitCode, 
	TareWeightMeasureType.unitCodeListVersionID, 
	TargetCurrencyBaseRateType.format, TargetServicePercentType.format, 
	TariffDescriptionType.languageID, 
	TariffDescriptionType.languageLocaleID, 
	TaxAmountType.currencyCodeListVersionID, TaxAmountType.currencyID, 
	TaxEnergyAmountType.currencyCodeListVersionID, 
	TaxEnergyAmountType.currencyID, 
	TaxEnergyBalanceAmountType.currencyCodeListVersionID, 
	TaxEnergyBalanceAmountType.currencyID, 
	TaxEnergyOnAccountAmountType.currencyCodeListVersionID, 
	TaxEnergyOnAccountAmountType.currencyID, 
	TaxExclusiveAmountType.currencyCodeListVersionID, 
	TaxExclusiveAmountType.currencyID, TaxExemptionReasonType.languageID, 
	TaxExemptionReasonType.languageLocaleID, 
	TaxInclusiveAmountType.currencyCodeListVersionID, 
	TaxInclusiveAmountType.currencyID, 
	TaxableAmountType.currencyCodeListVersionID, 
	TaxableAmountType.currencyID, 
	TechnicalCommitteeDescriptionType.languageID, 
	TechnicalCommitteeDescriptionType.languageLocaleID, 
	TechnicalNameType.languageID, TechnicalNameType.languageLocaleID, 
	TelecommunicationsServiceCallType.languageID, 
	TelecommunicationsServiceCallType.languageLocaleID, 
	TelecommunicationsServiceCategoryType.languageID, 
	TelecommunicationsServiceCategoryType.languageLocaleID, 
	TelecommunicationsSupplyTypeType.languageID, 
	TelecommunicationsSupplyTypeType.languageLocaleID, 
	TelefaxType.languageID, TelefaxType.languageLocaleID, 
	TelephoneType.languageID, TelephoneType.languageLocaleID, 
	TestMethodType.languageID, TestMethodType.languageLocaleID, 
	TextType.languageID, TextType.languageLocaleID, 
	ThresholdAmountType.currencyCodeListVersionID, 
	ThresholdAmountType.currencyID, TierRangeType.languageID, 
	TierRangeType.languageLocaleID, TierRatePercentType.format, 
	TimeAmountType.languageID, TimeAmountType.languageLocaleID, 
	TimezoneOffsetType.languageID, TimezoneOffsetType.languageLocaleID, 
	TimingComplaintType.languageID, TimingComplaintType.languageLocaleID, 
	TitleType.languageID, TitleType.languageLocaleID, 
	TotalAmountType.currencyCodeListVersionID, TotalAmountType.currencyID,
	TotalBalanceAmountType.currencyCodeListVersionID, 
	TotalBalanceAmountType.currencyID, 
	TotalCreditAmountType.currencyCodeListVersionID, 
	TotalCreditAmountType.currencyID, 
	TotalDebitAmountType.currencyCodeListVersionID, 
	TotalDebitAmountType.currencyID, 
	TotalInvoiceAmountType.currencyCodeListVersionID, 
	TotalInvoiceAmountType.currencyID, 
	TotalPaymentAmountType.currencyCodeListVersionID, 
	TotalPaymentAmountType.currencyID, 
	TotalTaskAmountType.currencyCodeListVersionID, 
	TotalTaskAmountType.currencyID, 
	TotalTaxAmountType.currencyCodeListVersionID, 
	TotalTaxAmountType.currencyID, TradingRestrictionsType.languageID, 
	TradingRestrictionsType.languageLocaleID, 
	TransactionCurrencyTaxAmountType.currencyCodeListVersionID, 
	TransactionCurrencyTaxAmountType.currencyID, 
	TransportServiceProviderRemarksType.languageID, 
	TransportServiceProviderRemarksType.languageLocaleID, 
	TransportServiceProviderSpecialTermsType.languageID, 
	TransportServiceProviderSpecialTermsType.languageLocaleID, 
	TransportUserRemarksType.languageID, 
	TransportUserRemarksType.languageLocaleID, 
	TransportUserSpecialTermsType.languageID, 
	TransportUserSpecialTermsType.languageLocaleID, 
	TransportationServiceDescriptionType.languageID, 
	TransportationServiceDescriptionType.languageLocaleID, 
	ValidateProcessType.languageID, ValidateProcessType.languageLocaleID, 
	ValidateToolType.languageID, ValidateToolType.languageLocaleID, 
	ValidateToolVersionType.languageID, 
	ValidateToolVersionType.languageLocaleID, 
	ValueAmountType.currencyCodeListVersionID, ValueAmountType.currencyID,
	ValueMeasureType.unitCode, ValueMeasureType.unitCodeListVersionID, 
	ValueQualifierType.languageID, ValueQualifierType.languageLocaleID, 
	ValueType.languageID, ValueType.languageLocaleID, 
	VesselNameType.languageID, VesselNameType.languageLocaleID, 
	WarrantyInformationType.languageID, 
	WarrantyInformationType.languageLocaleID, WeightNumericType.format, 
	WeightType.languageID, WeightType.languageLocaleID, 
	XPathType.languageID, XPathType.languageLocaleID
    ATTRIBUTE ALL IN AccountFormatCodeType, ALL IN AccountIDType, 
	ALL IN AccountTypeCodeType, ALL IN AccountingCostCodeType, 
	ALL IN ActionCodeType, ALL IN ActivityCodeType, 
	ALL IN ActualTemperatureReductionQuantityType, 
	ALL IN AdditionalAccountIDType, ALL IN AddressFormatCodeType, 
	ALL IN AddressTypeCodeType, ALL IN AdjustmentReasonCodeType, 
	ALL IN AdmissionCodeType, ALL IN AgencyIDType, ALL IN AircraftIDType, 
	ALL IN AllowanceChargeReasonCodeType, 
	ALL IN ApplicationStatusCodeType, ALL IN AttributeIDType, 
	ALL IN AuctionURIType, ALL IN AvailabilityStatusCodeType, 
	ALL IN AwardingCriteriaIDType, ALL IN AwardingCriteriaTypeCodeType, 
	ALL IN AwardingMethodTypeCodeType, ALL IN BackorderQuantityType, 
	ALL IN BaseQuantityType, ALL IN BasicConsumedQuantityType, 
	ALL IN BatchQuantityType, ALL IN BrokerAssignedIDType, 
	ALL IN BusinessClassificationEvidenceIDType, 
	ALL IN BusinessIdentityEvidenceIDType, ALL IN BuyerEventIDType, 
	ALL IN BuyerProfileURIType, ALL IN CV2IDType, 
	ALL IN CalculationExpressionCodeType, ALL IN CapabilityTypeCodeType, 
	ALL IN CardChipCodeType, ALL IN CardTypeCodeType, 
	ALL IN CargoTypeCodeType, ALL IN CarrierAssignedIDType, 
	ALL IN CertificateTypeCodeType, ALL IN ChannelCodeType, 
	ALL IN CharacterSetCodeType, ALL IN ChargeableQuantityType, 
	ALL IN ChipApplicationIDType, ALL IN ClauseCodeType, 
	ALL IN CollaborationPriorityCodeType, ALL IN CommodityCodeType, 
	ALL IN CompanyIDType, ALL IN CompanyLegalFormCodeType, 
	ALL IN CompanyLiquidationStatusCodeType, 
	ALL IN ComparisonDataCodeType, ALL IN ComparisonDataSourceCodeType, 
	ALL IN ConditionCodeType, ALL IN ConsigneeAssignedIDType, 
	ALL IN ConsignmentQuantityType, ALL IN ConsignorAssignedIDType, 
	ALL IN ConstitutionCodeType, 
	ALL IN ConsumerIncentiveTacticTypeCodeType, 
	ALL IN ConsumerUnitQuantityType, ALL IN ConsumersEnergyLevelCodeType, 
	ALL IN ConsumptionEnergyQuantityType, ALL IN ConsumptionIDType, 
	ALL IN ConsumptionLevelCodeType, ALL IN ConsumptionReportIDType, 
	ALL IN ConsumptionTypeCodeType, ALL IN ConsumptionWaterQuantityType, 
	ALL IN ContentUnitQuantityType, ALL IN ContractFolderIDType, 
	ALL IN ContractTypeCodeType, ALL IN ContractedCarrierAssignedIDType, 
	ALL IN ContractingPartyTypeCodeType, ALL IN ContractingSystemCodeType,
	ALL IN CoordinateSystemCodeType, 
	ALL IN CorporateRegistrationTypeCodeType, 
	ALL IN CorrectionTypeCodeType, ALL IN CountrySubentityCodeType, 
	ALL IN CreditedQuantityType, ALL IN CurrencyCodeType, 
	ALL IN CurrentChargeTypeCodeType, 
	ALL IN CustomerAssignedAccountIDType, ALL IN CustomizationIDType, 
	ALL IN CustomsStatusCodeType, ALL IN CustomsTariffQuantityType, 
	ALL IN DataSourceCodeType, ALL IN DebitedQuantityType, 
	ALL IN DeclarationTypeCodeType, ALL IN DeliveredQuantityType, 
	ALL IN DescriptionCodeType, ALL IN DespatchAdviceTypeCodeType, 
	ALL IN DifferenceTemperatureReductionQuantityType, 
	ALL IN DirectionCodeType, ALL IN DisplayTacticTypeCodeType, 
	ALL IN DispositionCodeType, ALL IN DocumentCurrencyCodeType, 
	ALL IN DocumentIDType, ALL IN DocumentStatusCodeType, 
	ALL IN DocumentTypeCodeType, ALL IN DutyCodeType, 
	ALL IN EconomicOperatorRegistryURIType, 
	ALL IN EmbeddedDocumentBinaryObjectType, 
	ALL IN EmergencyProceduresCodeType, ALL IN EmployeeQuantityType, 
	ALL IN EncodingCodeType, ALL IN EndpointIDType, 
	ALL IN EnvironmentalEmissionTypeCodeType, 
	ALL IN EstimatedConsumedQuantityType, 
	ALL IN EstimatedOverallContractQuantityType, 
	ALL IN EvaluationCriteriaTypeCodeType, ALL IN EvidenceSuppliedIDType, 
	ALL IN EvidenceTypeCodeType, ALL IN ExceptionResolutionCodeType, 
	ALL IN ExceptionStatusCodeType, ALL IN ExchangeMarketIDType, 
	ALL IN ExecutionRequirementCodeType, ALL IN ExemptionReasonCodeType, 
	ALL IN ExpectedOperatorQuantityType, ALL IN ExpectedQuantityType, 
	ALL IN ExpenseCodeType, ALL IN ExpressionCodeType, 
	ALL IN ExtendedIDType, ALL IN FeatureTacticTypeCodeType, 
	ALL IN FinancingInstrumentCodeType, ALL IN ForecastPurposeCodeType, 
	ALL IN ForecastTypeCodeType, ALL IN FormatCodeType, 
	ALL IN FreightForwarderAssignedIDType, 
	ALL IN FreightRateClassCodeType, ALL IN FullnessIndicationCodeType, 
	ALL IN FundingProgramCodeType, ALL IN GasPressureQuantityType, 
	ALL IN GenderCodeType, ALL IN GuaranteeTypeCodeType, 
	ALL IN HandlingCodeType, ALL IN HazardClassIDType, 
	ALL IN HazardousCategoryCodeType, ALL IN HazardousRegulationCodeType, 
	ALL IN HeatingTypeCodeType, ALL IN IDType, 
	ALL IN IdentificationCodeType, ALL IN IdentificationIDType, 
	ALL IN ImmobilizationCertificateIDType, ALL IN ImportanceCodeType, 
	ALL IN IndustryClassificationCodeType, ALL IN InformationURIType, 
	ALL IN InhalationToxicityZoneCodeType, 
	ALL IN InspectionMethodCodeType, ALL IN InstructionIDType, 
	ALL IN InterestedProcurementLotsIDType, ALL IN InvoiceTypeCodeType, 
	ALL IN InvoicedQuantityType, ALL IN IssueNumberIDType, 
	ALL IN IssuerIDType, ALL IN ItemClassificationCodeType, 
	ALL IN JourneyIDType, ALL IN LanguageIDType, 
	ALL IN LatestMeterQuantityType, ALL IN LatitudeDirectionCodeType, 
	ALL IN LicensePlateIDType, ALL IN LifeCycleStatusCodeType, 
	ALL IN LineIDType, ALL IN LineStatusCodeType, 
	ALL IN LoadingSequenceIDType, ALL IN LocaleCodeType, 
	ALL IN LocationIDType, ALL IN LocationTypeCodeType, 
	ALL IN LogoReferenceIDType, ALL IN LongitudeDirectionCodeType, 
	ALL IN LossRiskResponsibilityCodeType, ALL IN LotNumberIDType, 
	ALL IN LowerOrangeHazardPlacardIDType, ALL IN MandateTypeCodeType, 
	ALL IN MarkingIDType, ALL IN MathematicOperatorCodeType, 
	ALL IN MaximumBackorderQuantityType, 
	ALL IN MaximumOperatorQuantityType, ALL IN MaximumOrderQuantityType, 
	ALL IN MaximumQuantityType, ALL IN MaximumVariantQuantityType, 
	ALL IN MedicalFirstAidGuideCodeType, ALL IN MeterConstantCodeType, 
	ALL IN MeterReadingMethodCodeType, ALL IN MeterReadingTypeCodeType, 
	ALL IN MimeCodeType, ALL IN MinimumBackorderQuantityType, 
	ALL IN MinimumInventoryQuantityType, ALL IN MinimumOrderQuantityType, 
	ALL IN MinimumQuantityType, ALL IN MiscellaneousEventTypeCodeType, 
	ALL IN MultipleOrderQuantityType, ALL IN NameCodeType, 
	ALL IN NationalityIDType, ALL IN NatureCodeType, ALL IN NetworkIDType,
	ALL IN NormalTemperatureReductionQuantityType, 
	ALL IN NotificationTypeCodeType, ALL IN OneTimeChargeTypeCodeType, 
	ALL IN OntologyURIType, ALL IN OpenTenderIDType, 
	ALL IN OperatingYearsQuantityType, ALL IN OperationStatusCodeType, 
	ALL IN OrderResponseCodeType, ALL IN OrderTypeCodeType, 
	ALL IN OriginalContractingSystemIDType, ALL IN OriginalJobIDType, 
	ALL IN OutstandingQuantityType, ALL IN OversupplyQuantityType, 
	ALL IN OwnerTypeCodeType, ALL IN PackLevelCodeType, 
	ALL IN PackQuantityType, ALL IN PackageLevelCodeType, 
	ALL IN PackagingTypeCodeType, ALL IN PackingCriteriaCodeType, 
	ALL IN ParentDocumentIDType, ALL IN ParentDocumentLineReferenceIDType,
	ALL IN ParentDocumentTypeCodeType, ALL IN ParentDocumentVersionIDType,
	ALL IN PartPresentationCodeType, 
	ALL IN PaymentAlternativeCurrencyCodeType, 
	ALL IN PaymentChannelCodeType, ALL IN PaymentCurrencyCodeType, 
	ALL IN PaymentFrequencyCodeType, ALL IN PaymentIDType, 
	ALL IN PaymentMeansCodeType, ALL IN PaymentMeansIDType, 
	ALL IN PaymentPurposeCodeType, ALL IN PaymentTermsDetailsURIType, 
	ALL IN PerformanceMetricTypeCodeType, 
	ALL IN PerformanceValueQuantityType, 
	ALL IN PerformingCarrierAssignedIDType, ALL IN PositionCodeType, 
	ALL IN PreferenceCriterionCodeType, 
	ALL IN PrepaidPaymentReferenceIDType, 
	ALL IN PreviousCancellationReasonCodeType, ALL IN PreviousJobIDType, 
	ALL IN PreviousMeterQuantityType, ALL IN PreviousVersionIDType, 
	ALL IN PriceEvaluationCodeType, ALL IN PriceTypeCodeType, 
	ALL IN PricingCurrencyCodeType, ALL IN PrimaryAccountNumberIDType, 
	ALL IN PrivacyCodeType, ALL IN ProcedureCodeType, 
	ALL IN ProcessReasonCodeType, ALL IN ProcurementProjectLotIDType, 
	ALL IN ProcurementSubTypeCodeType, ALL IN ProcurementTypeCodeType, 
	ALL IN ProductTraceIDType, ALL IN ProfileExecutionIDType, 
	ALL IN ProfileIDType, ALL IN ProfileStatusCodeType, 
	ALL IN PromotionalEventTypeCodeType, ALL IN ProviderTypeCodeType, 
	ALL IN PurposeCodeType, ALL IN QualityControlCodeType, 
	ALL IN QuantityDiscrepancyCodeType, ALL IN QuantityType, 
	ALL IN RailCarIDType, ALL IN ReceivedQuantityType, 
	ALL IN ReceivedTenderQuantityType, ALL IN ReferenceEventCodeType, 
	ALL IN ReferenceIDType, ALL IN ReferencedConsignmentIDType, 
	ALL IN RegistrationIDType, ALL IN RegistrationNationalityIDType, 
	ALL IN RejectActionCodeType, ALL IN RejectReasonCodeType, 
	ALL IN RejectedQuantityType, ALL IN ReleaseIDType, 
	ALL IN ReminderTypeCodeType, ALL IN RequestForQuotationLineIDType, 
	ALL IN RequestedInvoiceCurrencyCodeType, ALL IN RequiredCustomsIDType,
	ALL IN ResidenceTypeCodeType, ALL IN ResolutionCodeType, 
	ALL IN ResponseCodeType, ALL IN RetailEventStatusCodeType, 
	ALL IN ReturnableQuantityType, ALL IN RevisedForecastLineIDType, 
	ALL IN RevisionStatusCodeType, ALL IN RoleCodeType, 
	ALL IN SalesOrderIDType, ALL IN SalesOrderLineIDType, 
	ALL IN SchemeURIType, ALL IN SealIssuerTypeCodeType, 
	ALL IN SealStatusCodeType, ALL IN SecurityClassificationCodeType, 
	ALL IN SecurityIDType, ALL IN SellerEventIDType, 
	ALL IN SequenceIDType, ALL IN SequenceNumberIDType, 
	ALL IN SerialIDType, ALL IN ServiceTypeCodeType, 
	ALL IN SharesNumberQuantityType, ALL IN ShippingOrderIDType, 
	ALL IN ShippingPriorityLevelCodeType, ALL IN ShortQuantityType, 
	ALL IN ShortageActionCodeType, ALL IN SignatureIDType, 
	ALL IN SizeTypeCodeType, ALL IN SourceCurrencyCodeType, 
	ALL IN SpecificationIDType, ALL IN SpecificationTypeCodeType, 
	ALL IN StatementTypeCodeType, ALL IN StatusCodeType, 
	ALL IN StatusReasonCodeType, ALL IN SubmissionMethodCodeType, 
	ALL IN SubscriberIDType-1, ALL IN SubscriberIDTypeCodeType, 
	ALL IN SubscriberTypeCodeType, ALL IN SubstitutionStatusCodeType, 
	ALL IN SuccessiveSequenceIDType, ALL IN SupplierAssignedAccountIDType,
	ALL IN SupplyChainActivityTypeCodeType, ALL IN TargetCurrencyCodeType,
	ALL IN TargetInventoryQuantityType, ALL IN TariffClassCodeType, 
	ALL IN TariffCodeType, ALL IN TaxCurrencyCodeType, 
	ALL IN TaxExemptionReasonCodeType, ALL IN TaxLevelCodeType, 
	ALL IN TaxTypeCodeType, ALL IN TelecommunicationsServiceCallCodeType, 
	ALL IN TelecommunicationsServiceCategoryCodeType, 
	ALL IN TelecommunicationsSupplyTypeCodeType, 
	ALL IN TenderEnvelopeIDType, ALL IN TenderEnvelopeTypeCodeType, 
	ALL IN TenderResultCodeType, ALL IN TenderTypeCodeType, 
	ALL IN TendererRequirementTypeCodeType, ALL IN ThresholdQuantityType, 
	ALL IN ThresholdValueComparisonCodeType, 
	ALL IN TimeDeltaDaysQuantityType, ALL IN TimeFrequencyCodeType, 
	ALL IN TimingComplaintCodeType, ALL IN TotalConsumedQuantityType, 
	ALL IN TotalDeliveredQuantityType, ALL IN TotalGoodsItemQuantityType, 
	ALL IN TotalMeteredQuantityType, ALL IN TotalPackageQuantityType, 
	ALL IN TotalPackagesQuantityType, 
	ALL IN TotalTransportHandlingUnitQuantityType, ALL IN TraceIDType, 
	ALL IN TrackingDeviceCodeType, ALL IN TrackingIDType, 
	ALL IN TradeItemPackingLabelingTypeCodeType, 
	ALL IN TradeServiceCodeType, ALL IN TrainIDType, 
	ALL IN TransitDirectionCodeType, 
	ALL IN TransportAuthorizationCodeType, 
	ALL IN TransportEmergencyCardCodeType, 
	ALL IN TransportEquipmentTypeCodeType, 
	ALL IN TransportEventTypeCodeType, 
	ALL IN TransportExecutionPlanReferenceIDType, 
	ALL IN TransportHandlingUnitTypeCodeType, 
	ALL IN TransportMeansTypeCodeType, ALL IN TransportModeCodeType, 
	ALL IN TransportServiceCodeType, 
	ALL IN TransportationServiceDetailsURIType, ALL IN TypeCodeType, 
	ALL IN UBLVersionIDType, ALL IN UNDGCodeType, ALL IN URIType, 
	ALL IN UUIDType, ALL IN UpperOrangeHazardPlacardIDType, 
	ALL IN UrgencyCodeType, ALL IN UtilityStatementTypeCodeType, 
	ALL IN ValidationResultCodeType, ALL IN ValidatorIDType, 
	ALL IN ValueQuantityType, ALL IN VarianceQuantityType, 
	ALL IN VariantIDType, ALL IN VersionIDType, ALL IN VesselIDType, 
	ALL IN WebsiteURIType, ALL IN WeightingAlgorithmCodeType
    NOT ATTRIBUTE AccountFormatCodeType.base, AccountIDType.base, 
	AccountTypeCodeType.base, AccountingCostCodeType.base, 
	ActionCodeType.base, ActivityCodeType.base, 
	ActualTemperatureReductionQuantityType.base, 
	AdditionalAccountIDType.base, AddressFormatCodeType.base, 
	AddressTypeCodeType.base, AdjustmentReasonCodeType.base, 
	AdmissionCodeType.base, AgencyIDType.base, AircraftIDType.base, 
	AllowanceChargeReasonCodeType.base, ApplicationStatusCodeType.base, 
	AttributeIDType.base, AuctionURIType.base, 
	AvailabilityStatusCodeType.base, AwardingCriteriaIDType.base, 
	AwardingCriteriaTypeCodeType.base, AwardingMethodTypeCodeType.base, 
	BackorderQuantityType.base, BaseQuantityType.base, 
	BasicConsumedQuantityType.base, BatchQuantityType.base, 
	BrokerAssignedIDType.base, BusinessClassificationEvidenceIDType.base, 
	BusinessIdentityEvidenceIDType.base, BuyerEventIDType.base, 
	BuyerProfileURIType.base, CV2IDType.base, 
	CalculationExpressionCodeType.base, CapabilityTypeCodeType.base, 
	CardChipCodeType.base, CardTypeCodeType.base, CargoTypeCodeType.base, 
	CarrierAssignedIDType.base, CertificateTypeCodeType.base, 
	ChannelCodeType.base, CharacterSetCodeType.base, 
	ChargeableQuantityType.base, ChipApplicationIDType.base, 
	ClauseCodeType.base, CollaborationPriorityCodeType.base, 
	CommodityCodeType.base, CompanyIDType.base, 
	CompanyLegalFormCodeType.base, CompanyLiquidationStatusCodeType.base, 
	ComparisonDataCodeType.base, ComparisonDataSourceCodeType.base, 
	ConditionCodeType.base, ConsigneeAssignedIDType.base, 
	ConsignmentQuantityType.base, ConsignorAssignedIDType.base, 
	ConstitutionCodeType.base, ConsumerIncentiveTacticTypeCodeType.base, 
	ConsumerUnitQuantityType.base, ConsumersEnergyLevelCodeType.base, 
	ConsumptionEnergyQuantityType.base, ConsumptionIDType.base, 
	ConsumptionLevelCodeType.base, ConsumptionReportIDType.base, 
	ConsumptionTypeCodeType.base, ConsumptionWaterQuantityType.base, 
	ContentUnitQuantityType.base, ContractFolderIDType.base, 
	ContractTypeCodeType.base, ContractedCarrierAssignedIDType.base, 
	ContractingPartyTypeCodeType.base, ContractingSystemCodeType.base, 
	CoordinateSystemCodeType.base, CorporateRegistrationTypeCodeType.base,
	CorrectionTypeCodeType.base, CountrySubentityCodeType.base, 
	CreditedQuantityType.base, CurrencyCodeType.base, 
	CurrentChargeTypeCodeType.base, CustomerAssignedAccountIDType.base, 
	CustomizationIDType.base, CustomsStatusCodeType.base, 
	CustomsTariffQuantityType.base, DataSourceCodeType.base, 
	DebitedQuantityType.base, DeclarationTypeCodeType.base, 
	DeliveredQuantityType.base, DescriptionCodeType.base, 
	DespatchAdviceTypeCodeType.base, 
	DifferenceTemperatureReductionQuantityType.base, 
	DirectionCodeType.base, DisplayTacticTypeCodeType.base, 
	DispositionCodeType.base, DocumentCurrencyCodeType.base, 
	DocumentIDType.base, DocumentStatusCodeType.base, 
	DocumentTypeCodeType.base, DutyCodeType.base, 
	EconomicOperatorRegistryURIType.base, 
	EmbeddedDocumentBinaryObjectType.base, 
	EmergencyProceduresCodeType.base, EmployeeQuantityType.base, 
	EncodingCodeType.base, EndpointIDType.base, 
	EnvironmentalEmissionTypeCodeType.base, 
	EstimatedConsumedQuantityType.base, 
	EstimatedOverallContractQuantityType.base, 
	EvaluationCriteriaTypeCodeType.base, EvidenceSuppliedIDType.base, 
	EvidenceTypeCodeType.base, ExceptionResolutionCodeType.base, 
	ExceptionStatusCodeType.base, ExchangeMarketIDType.base, 
	ExecutionRequirementCodeType.base, ExemptionReasonCodeType.base, 
	ExpectedOperatorQuantityType.base, ExpectedQuantityType.base, 
	ExpenseCodeType.base, ExpressionCodeType.base, ExtendedIDType.base, 
	FeatureTacticTypeCodeType.base, FinancingInstrumentCodeType.base, 
	ForecastPurposeCodeType.base, ForecastTypeCodeType.base, 
	FormatCodeType.base, FreightForwarderAssignedIDType.base, 
	FreightRateClassCodeType.base, FullnessIndicationCodeType.base, 
	FundingProgramCodeType.base, GasPressureQuantityType.base, 
	GenderCodeType.base, GuaranteeTypeCodeType.base, 
	HandlingCodeType.base, HazardClassIDType.base, 
	HazardousCategoryCodeType.base, HazardousRegulationCodeType.base, 
	HeatingTypeCodeType.base, IDType.base, IdentificationCodeType.base, 
	IdentificationIDType.base, ImmobilizationCertificateIDType.base, 
	ImportanceCodeType.base, IndustryClassificationCodeType.base, 
	InformationURIType.base, InhalationToxicityZoneCodeType.base, 
	InspectionMethodCodeType.base, InstructionIDType.base, 
	InterestedProcurementLotsIDType.base, InvoiceTypeCodeType.base, 
	InvoicedQuantityType.base, IssueNumberIDType.base, IssuerIDType.base, 
	ItemClassificationCodeType.base, JourneyIDType.base, 
	LanguageIDType.base, LatestMeterQuantityType.base, 
	LatitudeDirectionCodeType.base, LicensePlateIDType.base, 
	LifeCycleStatusCodeType.base, LineIDType.base, 
	LineStatusCodeType.base, LoadingSequenceIDType.base, 
	LocaleCodeType.base, LocationIDType.base, LocationTypeCodeType.base, 
	LogoReferenceIDType.base, LongitudeDirectionCodeType.base, 
	LossRiskResponsibilityCodeType.base, LotNumberIDType.base, 
	LowerOrangeHazardPlacardIDType.base, MandateTypeCodeType.base, 
	MarkingIDType.base, MathematicOperatorCodeType.base, 
	MaximumBackorderQuantityType.base, MaximumOperatorQuantityType.base, 
	MaximumOrderQuantityType.base, MaximumQuantityType.base, 
	MaximumVariantQuantityType.base, MedicalFirstAidGuideCodeType.base, 
	MeterConstantCodeType.base, MeterReadingMethodCodeType.base, 
	MeterReadingTypeCodeType.base, MimeCodeType.base, 
	MinimumBackorderQuantityType.base, MinimumInventoryQuantityType.base, 
	MinimumOrderQuantityType.base, MinimumQuantityType.base, 
	MiscellaneousEventTypeCodeType.base, MultipleOrderQuantityType.base, 
	NameCodeType.base, NationalityIDType.base, NatureCodeType.base, 
	NetworkIDType.base, NormalTemperatureReductionQuantityType.base, 
	NotificationTypeCodeType.base, OneTimeChargeTypeCodeType.base, 
	OntologyURIType.base, OpenTenderIDType.base, 
	OperatingYearsQuantityType.base, OperationStatusCodeType.base, 
	OrderResponseCodeType.base, OrderTypeCodeType.base, 
	OriginalContractingSystemIDType.base, OriginalJobIDType.base, 
	OutstandingQuantityType.base, OversupplyQuantityType.base, 
	OwnerTypeCodeType.base, PackLevelCodeType.base, PackQuantityType.base,
	PackageLevelCodeType.base, PackagingTypeCodeType.base, 
	PackingCriteriaCodeType.base, ParentDocumentIDType.base, 
	ParentDocumentLineReferenceIDType.base, 
	ParentDocumentTypeCodeType.base, ParentDocumentVersionIDType.base, 
	PartPresentationCodeType.base, 
	PaymentAlternativeCurrencyCodeType.base, PaymentChannelCodeType.base, 
	PaymentCurrencyCodeType.base, PaymentFrequencyCodeType.base, 
	PaymentIDType.base, PaymentMeansCodeType.base, 
	PaymentMeansIDType.base, PaymentPurposeCodeType.base, 
	PaymentTermsDetailsURIType.base, PerformanceMetricTypeCodeType.base, 
	PerformanceValueQuantityType.base, 
	PerformingCarrierAssignedIDType.base, PositionCodeType.base, 
	PreferenceCriterionCodeType.base, PrepaidPaymentReferenceIDType.base, 
	PreviousCancellationReasonCodeType.base, PreviousJobIDType.base, 
	PreviousMeterQuantityType.base, PreviousVersionIDType.base, 
	PriceEvaluationCodeType.base, PriceTypeCodeType.base, 
	PricingCurrencyCodeType.base, PrimaryAccountNumberIDType.base, 
	PrivacyCodeType.base, ProcedureCodeType.base, 
	ProcessReasonCodeType.base, ProcurementProjectLotIDType.base, 
	ProcurementSubTypeCodeType.base, ProcurementTypeCodeType.base, 
	ProductTraceIDType.base, ProfileExecutionIDType.base, 
	ProfileIDType.base, ProfileStatusCodeType.base, 
	PromotionalEventTypeCodeType.base, ProviderTypeCodeType.base, 
	PurposeCodeType.base, QualityControlCodeType.base, 
	QuantityDiscrepancyCodeType.base, QuantityType.base, 
	RailCarIDType.base, ReceivedQuantityType.base, 
	ReceivedTenderQuantityType.base, ReferenceEventCodeType.base, 
	ReferenceIDType.base, ReferencedConsignmentIDType.base, 
	RegistrationIDType.base, RegistrationNationalityIDType.base, 
	RejectActionCodeType.base, RejectReasonCodeType.base, 
	RejectedQuantityType.base, ReleaseIDType.base, 
	ReminderTypeCodeType.base, RequestForQuotationLineIDType.base, 
	RequestedInvoiceCurrencyCodeType.base, RequiredCustomsIDType.base, 
	ResidenceTypeCodeType.base, ResolutionCodeType.base, 
	ResponseCodeType.base, RetailEventStatusCodeType.base, 
	ReturnableQuantityType.base, RevisedForecastLineIDType.base, 
	RevisionStatusCodeType.base, RoleCodeType.base, SalesOrderIDType.base,
	SalesOrderLineIDType.base, SchemeURIType.base, 
	SealIssuerTypeCodeType.base, SealStatusCodeType.base, 
	SecurityClassificationCodeType.base, SecurityIDType.base, 
	SellerEventIDType.base, SequenceIDType.base, 
	SequenceNumberIDType.base, SerialIDType.base, 
	ServiceTypeCodeType.base, SharesNumberQuantityType.base, 
	ShippingOrderIDType.base, ShippingPriorityLevelCodeType.base, 
	ShortQuantityType.base, ShortageActionCodeType.base, 
	SignatureIDType.base, SizeTypeCodeType.base, 
	SourceCurrencyCodeType.base, SpecificationIDType.base, 
	SpecificationTypeCodeType.base, StatementTypeCodeType.base, 
	StatusCodeType.base, StatusReasonCodeType.base, 
	SubmissionMethodCodeType.base, SubscriberIDType-1.base, 
	SubscriberIDTypeCodeType.base, SubscriberTypeCodeType.base, 
	SubstitutionStatusCodeType.base, SuccessiveSequenceIDType.base, 
	SupplierAssignedAccountIDType.base, 
	SupplyChainActivityTypeCodeType.base, TargetCurrencyCodeType.base, 
	TargetInventoryQuantityType.base, TariffClassCodeType.base, 
	TariffCodeType.base, TaxCurrencyCodeType.base, 
	TaxExemptionReasonCodeType.base, TaxLevelCodeType.base, 
	TaxTypeCodeType.base, TelecommunicationsServiceCallCodeType.base, 
	TelecommunicationsServiceCategoryCodeType.base, 
	TelecommunicationsSupplyTypeCodeType.base, TenderEnvelopeIDType.base, 
	TenderEnvelopeTypeCodeType.base, TenderResultCodeType.base, 
	TenderTypeCodeType.base, TendererRequirementTypeCodeType.base, 
	ThresholdQuantityType.base, ThresholdValueComparisonCodeType.base, 
	TimeDeltaDaysQuantityType.base, TimeFrequencyCodeType.base, 
	TimingComplaintCodeType.base, TotalConsumedQuantityType.base, 
	TotalDeliveredQuantityType.base, TotalGoodsItemQuantityType.base, 
	TotalMeteredQuantityType.base, TotalPackageQuantityType.base, 
	TotalPackagesQuantityType.base, 
	TotalTransportHandlingUnitQuantityType.base, TraceIDType.base, 
	TrackingDeviceCodeType.base, TrackingIDType.base, 
	TradeItemPackingLabelingTypeCodeType.base, TradeServiceCodeType.base, 
	TrainIDType.base, TransitDirectionCodeType.base, 
	TransportAuthorizationCodeType.base, 
	TransportEmergencyCardCodeType.base, 
	TransportEquipmentTypeCodeType.base, TransportEventTypeCodeType.base, 
	TransportExecutionPlanReferenceIDType.base, 
	TransportHandlingUnitTypeCodeType.base, 
	TransportMeansTypeCodeType.base, TransportModeCodeType.base, 
	TransportServiceCodeType.base, 
	TransportationServiceDetailsURIType.base, TypeCodeType.base, 
	UBLVersionIDType.base, UNDGCodeType.base, URIType.base, UUIDType.base,
	UpperOrangeHazardPlacardIDType.base, UrgencyCodeType.base, 
	UtilityStatementTypeCodeType.base, ValidationResultCodeType.base, 
	ValidatorIDType.base, ValueQuantityType.base, 
	VarianceQuantityType.base, VariantIDType.base, VersionIDType.base, 
	VesselIDType.base, WebsiteURIType.base, 
	WeightingAlgorithmCodeType.base
    BASE64 EmbeddedDocumentBinaryObjectType.base
    UNTAGGED base IN ALL
END
