CatalogueRequest-2
DEFINITIONS AUTOMATIC TAGS ::=
BEGIN
IMPORTS 
    UBLExtensions
    FROM CommonExtensionComponents-2
    UBLVersionID, CustomizationID, ProfileID, ProfileExecutionID, ID-1, UUID, 
    Name-1, IssueDate, IssueTime, Note, Description, 
    PricingUpdateRequestIndicator, ItemUpdateRequestIndicator, 
    LineCountNumeric
    FROM CommonBasicComponents-2
    ValidityPeriod, Signature-1, ReceiverParty, ProviderParty, 
    SellerSupplierParty, ContractorCustomerParty, RequestedCatalogueReference,
    ReferencedContract, TradingTerms, DocumentReference, 
    ApplicableTerritoryAddress, RequestedLanguage, 
    RequestedClassificationScheme, CatalogueRequestLine
    FROM CommonAggregateComponents-2;

CatalogueRequest ::= CatalogueRequestType

CatalogueRequestType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    uUID       UUID OPTIONAL,
    name       Name-1 OPTIONAL,
    issueDate  IssueDate,
    issueTime  IssueTime OPTIONAL,
    note-list  SEQUENCE OF note Note,
    description-list SEQUENCE OF description Description,
    pricingUpdateRequestIndicator PricingUpdateRequestIndicator OPTIONAL,
    itemUpdateRequestIndicator ItemUpdateRequestIndicator OPTIONAL,
    lineCountNumeric LineCountNumeric OPTIONAL,
    validityPeriod-list SEQUENCE OF validityPeriod ValidityPeriod,
    signature-list SEQUENCE OF signature Signature-1,
    receiverParty ReceiverParty,
    providerParty ProviderParty,
    sellerSupplierParty SellerSupplierParty OPTIONAL,
    contractorCustomerParty ContractorCustomerParty OPTIONAL,
    requestedCatalogueReference RequestedCatalogueReference OPTIONAL,
    referencedContract-list SEQUENCE OF referencedContract ReferencedContract,
    tradingTerms TradingTerms OPTIONAL,
    documentReference-list SEQUENCE OF documentReference DocumentReference,
    applicableTerritoryAddress-list SEQUENCE OF applicableTerritoryAddress 
	ApplicableTerritoryAddress,
    requestedLanguage RequestedLanguage OPTIONAL,
    requestedClassificationScheme-list SEQUENCE OF 
	requestedClassificationScheme RequestedClassificationScheme,
    catalogueRequestLine-list SEQUENCE OF catalogueRequestLine 
	CatalogueRequestLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:CatalogueRequest-2"
	PREFIX "ns9"
    NAMESPACE CatalogueRequestType.uBLExtensions
	AS "urn:oasis:names:specification:ubl:schema:xsd:CommonExtensionComponents-2"
	    PREFIX "ext"
    NAMESPACE CatalogueRequestType.uBLVersionID, 
	CatalogueRequestType.customizationID, CatalogueRequestType.profileID, 
	CatalogueRequestType.profileExecutionID, CatalogueRequestType.iD, 
	CatalogueRequestType.uUID, CatalogueRequestType.name, 
	CatalogueRequestType.issueDate, CatalogueRequestType.issueTime, 
	CatalogueRequestType.note-list.note, 
	CatalogueRequestType.description-list.description, 
	CatalogueRequestType.pricingUpdateRequestIndicator, 
	CatalogueRequestType.itemUpdateRequestIndicator, 
	CatalogueRequestType.lineCountNumeric
	AS "urn:oasis:names:specification:ubl:schema:xsd:CommonBasicComponents-2"
	    PREFIX "cbc"
    NAMESPACE CatalogueRequestType.validityPeriod-list.validityPeriod, 
	CatalogueRequestType.signature-list.signature, 
	CatalogueRequestType.receiverParty, 
	CatalogueRequestType.providerParty, 
	CatalogueRequestType.sellerSupplierParty, 
	CatalogueRequestType.contractorCustomerParty, 
	CatalogueRequestType.requestedCatalogueReference, 
	CatalogueRequestType.referencedContract-list.referencedContract, 
	CatalogueRequestType.tradingTerms, 
	CatalogueRequestType.documentReference-list.documentReference, 
	CatalogueRequestType.applicableTerritoryAddress-list.applicableTerritoryAddress,
	CatalogueRequestType.requestedLanguage, 
	CatalogueRequestType.requestedClassificationScheme-list.requestedClassificationScheme,
	CatalogueRequestType.catalogueRequestLine-list.catalogueRequestLine
	AS "urn:oasis:names:specification:ubl:schema:xsd:CommonAggregateComponents-2"
	    PREFIX "cac"
    NAME CatalogueRequestType.uBLExtensions, 
	CatalogueRequestType.uBLVersionID, 
	CatalogueRequestType.customizationID, CatalogueRequestType.profileID, 
	CatalogueRequestType.profileExecutionID, CatalogueRequestType.iD, 
	CatalogueRequestType.uUID, CatalogueRequestType.name, 
	CatalogueRequestType.issueDate, CatalogueRequestType.issueTime, 
	CatalogueRequestType.note-list.note, 
	CatalogueRequestType.description-list.description, 
	CatalogueRequestType.pricingUpdateRequestIndicator, 
	CatalogueRequestType.itemUpdateRequestIndicator, 
	CatalogueRequestType.lineCountNumeric, 
	CatalogueRequestType.validityPeriod-list.validityPeriod, 
	CatalogueRequestType.signature-list.signature, 
	CatalogueRequestType.receiverParty, 
	CatalogueRequestType.providerParty, 
	CatalogueRequestType.sellerSupplierParty, 
	CatalogueRequestType.contractorCustomerParty, 
	CatalogueRequestType.requestedCatalogueReference, 
	CatalogueRequestType.referencedContract-list.referencedContract, 
	CatalogueRequestType.tradingTerms, 
	CatalogueRequestType.documentReference-list.documentReference, 
	CatalogueRequestType.applicableTerritoryAddress-list.applicableTerritoryAddress,
	CatalogueRequestType.requestedLanguage, 
	CatalogueRequestType.requestedClassificationScheme-list.requestedClassificationScheme,
	CatalogueRequestType.catalogueRequestLine-list.catalogueRequestLine
	AS CAPITALIZED
    UNTAGGED SEQUENCE OF
END
