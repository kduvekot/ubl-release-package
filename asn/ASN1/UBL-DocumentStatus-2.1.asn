DocumentStatus-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note
    FROM CommonBasicComponents-2
    Signature-1, SenderParty, ReceiverParty, DocumentResponse, 
    AdditionalDocumentResponse
    FROM CommonAggregateComponents-2;

DocumentStatus ::= DocumentStatusType

DocumentStatusType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    signature-list SEQUENCE OF signature Signature-1,
    senderParty SenderParty OPTIONAL,
    receiverParty ReceiverParty OPTIONAL,
    documentResponse DocumentResponse,
    additionalDocumentResponse-list SEQUENCE OF additionalDocumentResponse 
	AdditionalDocumentResponse
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:DocumentStatus-2"
	PREFIX "ns16"
    NAMESPACE DocumentStatusType.uBLExtensions
	AS "urn:oasis:names:specification:ubl:schema:xsd:CommonExtensionComponents-2"
	    PREFIX "ext"
    NAMESPACE DocumentStatusType.uBLVersionID, 
	DocumentStatusType.customizationID, DocumentStatusType.profileID, 
	DocumentStatusType.profileExecutionID, DocumentStatusType.iD, 
	DocumentStatusType.copyIndicator, DocumentStatusType.uUID, 
	DocumentStatusType.issueDate, DocumentStatusType.issueTime, 
	DocumentStatusType.note-list.note
	AS "urn:oasis:names:specification:ubl:schema:xsd:CommonBasicComponents-2"
	    PREFIX "cbc"
    NAMESPACE DocumentStatusType.signature-list.signature, 
	DocumentStatusType.senderParty, DocumentStatusType.receiverParty, 
	DocumentStatusType.documentResponse, 
	DocumentStatusType.additionalDocumentResponse-list.additionalDocumentResponse
	AS "urn:oasis:names:specification:ubl:schema:xsd:CommonAggregateComponents-2"
	    PREFIX "cac"
    NAME DocumentStatusType.uBLExtensions, DocumentStatusType.uBLVersionID, 
	DocumentStatusType.customizationID, DocumentStatusType.profileID, 
	DocumentStatusType.profileExecutionID, DocumentStatusType.iD, 
	DocumentStatusType.copyIndicator, DocumentStatusType.uUID, 
	DocumentStatusType.issueDate, DocumentStatusType.issueTime, 
	DocumentStatusType.note-list.note, 
	DocumentStatusType.signature-list.signature, 
	DocumentStatusType.senderParty, DocumentStatusType.receiverParty, 
	DocumentStatusType.documentResponse, 
	DocumentStatusType.additionalDocumentResponse-list.additionalDocumentResponse
	AS CAPITALIZED
    UNTAGGED SEQUENCE OF
END
