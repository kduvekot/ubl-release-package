V1-3-2
DEFINITIONS AUTOMATIC TAGS ::=
BEGIN
IMPORTS 
    String, AnyURI, ID, DateTime, AnyType
    FROM XSD
    DigestMethod, DigestValue, CanonicalizationMethod, X509IssuerSerialType, 
    Transforms, Signature
    FROM Xmldsig;

Any ::= AnyType-1

AnyType-1 ::= SEQUENCE {
    embed-values  SEQUENCE OF XSD.String,
    attr          SEQUENCE (CONSTRAINED BY
		  {/* Each item shall conform to the
		  "AnyAttributeFormat" specified in ITU-T Rec. X.693 |
		  ISO/IEC 8825-4, clause 18 */}) OF XSD.String,
    sequence-list SEQUENCE OF SEQUENCE {
	elem XSD.String (CONSTRAINED BY
	     {/* Shall conform to the "AnyElementFormat" specified in ITU-T
	     Rec. X.693 | ISO/IEC 8825-4, clause 19 */})
    }
} (CONSTRAINED BY
    {/* Shall conform to ITU-T Rec. X.693 | ISO/IEC 8825-4, clause 25 */})

ObjectIdentifier ::= ObjectIdentifierType

ObjectIdentifierType ::= SEQUENCE {
    identifier       IdentifierType,
    description      XSD.String OPTIONAL,
    documentationReferences DocumentationReferencesType OPTIONAL
}

IdentifierType ::= SEQUENCE {
    qualifier QualifierType OPTIONAL,
    base      XSD.AnyURI
}

QualifierType ::= ENUMERATED {
    oIDAsURI,
    oIDAsURN
}

DocumentationReferencesType ::= SEQUENCE {
    sequence-list SEQUENCE (SIZE(1..MAX)) OF SEQUENCE {
	documentationReference XSD.AnyURI
    }
}

EncapsulatedPKIData ::= EncapsulatedPKIDataType

EncapsulatedPKIDataType ::= SEQUENCE {
    encoding XSD.AnyURI OPTIONAL,
    id       XSD.ID OPTIONAL,
    base     OCTET STRING
}

Include ::= IncludeType

IncludeType ::= SEQUENCE {
    uRI            XSD.AnyURI,
    referencedData BOOLEAN OPTIONAL
}

ReferenceInfo ::= ReferenceInfoType

ReferenceInfoType ::= SEQUENCE {
    id           XSD.ID OPTIONAL,
    uRI          XSD.AnyURI OPTIONAL,
    digestMethod DigestMethod,
    digestValue  DigestValue
}

GenericTimeStampType ::= SEQUENCE {
    id           XSD.ID OPTIONAL,
    choice       CHOICE {
	include-list       SEQUENCE OF include Include,
	referenceInfo-list SEQUENCE (SIZE(1..MAX)) OF referenceInfo 
			   ReferenceInfo
    } OPTIONAL,
    canonicalizationMethod CanonicalizationMethod OPTIONAL,
    choice-list  SEQUENCE (SIZE(1..MAX)) OF CHOICE {
	encapsulatedTimeStamp EncapsulatedPKIDataType,
	xMLTimeStamp     AnyType-1
    }
}

XAdESTimeStamp ::= XAdESTimeStampType

XAdESTimeStampType ::= SEQUENCE {
    id           XSD.ID OPTIONAL,
    include-list SEQUENCE OF include Include,
    canonicalizationMethod CanonicalizationMethod OPTIONAL,
    choice-list  SEQUENCE (SIZE(1..MAX)) OF CHOICE {
	encapsulatedTimeStamp EncapsulatedPKIDataType,
	xMLTimeStamp     AnyType-1
    }
}

OtherTimeStamp ::= OtherTimeStampType

OtherTimeStampType ::= SEQUENCE {
    id           XSD.ID OPTIONAL,
    referenceInfo-list SEQUENCE (SIZE(1..MAX)) OF referenceInfo ReferenceInfo,
    canonicalizationMethod CanonicalizationMethod OPTIONAL,
    choice       CHOICE {
	encapsulatedTimeStamp EncapsulatedPKIDataType,
	xMLTimeStamp     AnyType-1
    }
}

QualifyingProperties ::= QualifyingPropertiesType

QualifyingPropertiesType ::= SEQUENCE {
    id                 XSD.ID OPTIONAL,
    target             XSD.AnyURI,
    signedProperties   SignedPropertiesType OPTIONAL,
    unsignedProperties UnsignedPropertiesType OPTIONAL
}

SignedProperties ::= SignedPropertiesType

SignedPropertiesType ::= SEQUENCE {
    id         XSD.ID OPTIONAL,
    signedSignatureProperties SignedSignaturePropertiesType OPTIONAL,
    signedDataObjectProperties SignedDataObjectPropertiesType OPTIONAL
}

UnsignedProperties ::= UnsignedPropertiesType

UnsignedPropertiesType ::= SEQUENCE {
    id         XSD.ID OPTIONAL,
    unsignedSignatureProperties UnsignedSignaturePropertiesType OPTIONAL,
    unsignedDataObjectProperties UnsignedDataObjectPropertiesType OPTIONAL
}

SignedSignatureProperties ::= SignedSignaturePropertiesType

SignedSignaturePropertiesType ::= SEQUENCE {
    id         XSD.ID OPTIONAL,
    signingTime XSD.DateTime OPTIONAL,
    signingCertificate CertIDListType OPTIONAL,
    signaturePolicyIdentifier SignaturePolicyIdentifierType OPTIONAL,
    signatureProductionPlace SignatureProductionPlaceType OPTIONAL,
    signerRole SignerRoleType OPTIONAL
}

SignedDataObjectProperties ::= SignedDataObjectPropertiesType

SignedDataObjectPropertiesType ::= SEQUENCE {
    id         XSD.ID OPTIONAL,
    dataObjectFormat-list SEQUENCE OF dataObjectFormat DataObjectFormatType,
    commitmentTypeIndication-list SEQUENCE OF commitmentTypeIndication 
	       CommitmentTypeIndicationType,
    allDataObjectsTimeStamp-list SEQUENCE OF allDataObjectsTimeStamp 
	       XAdESTimeStampType,
    individualDataObjectsTimeStamp-list SEQUENCE OF 
	       individualDataObjectsTimeStamp XAdESTimeStampType
}

UnsignedSignatureProperties ::= UnsignedSignaturePropertiesType

UnsignedSignaturePropertiesType ::= SEQUENCE {
    id          XSD.ID OPTIONAL,
    choice-list SEQUENCE (SIZE(1..MAX)) OF CHOICE {
	counterSignature CounterSignatureType,
	signatureTimeStamp XAdESTimeStampType,
	completeCertificateRefs CompleteCertificateRefsType,
	completeRevocationRefs CompleteRevocationRefsType,
	attributeCertificateRefs CompleteCertificateRefsType,
	attributeRevocationRefs CompleteRevocationRefsType,
	sigAndRefsTimeStamp XAdESTimeStampType,
	refsOnlyTimeStamp XAdESTimeStampType,
	certificateValues CertificateValuesType,
	revocationValues RevocationValuesType,
	attrAuthoritiesCertValues CertificateValuesType,
	attributeRevocationValues RevocationValuesType,
	archiveTimeStamp XAdESTimeStampType,
	elem         XSD.String (CONSTRAINED BY
		     {/* Shall conform to the "AnyElementFormat" specified
		     in ITU-T Rec. X.693 | ISO/IEC 8825-4, clause 19 */})
    }
}

UnsignedDataObjectProperties ::= UnsignedDataObjectPropertiesType

UnsignedDataObjectPropertiesType ::= SEQUENCE {
    id         XSD.ID OPTIONAL,
    unsignedDataObjectProperty-list SEQUENCE (SIZE(1..MAX)) OF 
	       unsignedDataObjectProperty AnyType-1
}

QualifyingPropertiesReference ::= QualifyingPropertiesReferenceType

QualifyingPropertiesReferenceType ::= SEQUENCE {
    id  XSD.ID OPTIONAL,
    uRI XSD.AnyURI
}

SigningTime ::= XSD.DateTime

SigningCertificate ::= CertIDListType

CertIDListType ::= SEQUENCE {
    cert-list SEQUENCE (SIZE(1..MAX)) OF cert CertIDType
}

CertIDType ::= SEQUENCE {
    uRI          XSD.AnyURI OPTIONAL,
    certDigest   DigestAlgAndValueType,
    issuerSerial X509IssuerSerialType
}

DigestAlgAndValueType ::= SEQUENCE {
    digestMethod DigestMethod,
    digestValue  DigestValue
}

SignaturePolicyIdentifier ::= SignaturePolicyIdentifierType

SignaturePolicyIdentifierType ::= SEQUENCE {
    choice CHOICE {
	signaturePolicyId      SignaturePolicyIdType,
	signaturePolicyImplied XSD.AnyType
    }
}

SignaturePolicyIdType ::= SEQUENCE {
    sigPolicyId         ObjectIdentifierType,
    transforms          Transforms OPTIONAL,
    sigPolicyHash       DigestAlgAndValueType,
    sigPolicyQualifiers SigPolicyQualifiersListType OPTIONAL
}

SigPolicyQualifiersListType ::= SEQUENCE {
    sigPolicyQualifier-list SEQUENCE (SIZE(1..MAX)) OF sigPolicyQualifier 
			    AnyType-1
}

SPURI ::= XSD.AnyURI

SPUserNotice ::= SPUserNoticeType

SPUserNoticeType ::= SEQUENCE {
    noticeRef    NoticeReferenceType OPTIONAL,
    explicitText XSD.String OPTIONAL
}

NoticeReferenceType ::= SEQUENCE {
    organization  XSD.String,
    noticeNumbers IntegerListType
}

IntegerListType ::= SEQUENCE {
    int-list SEQUENCE OF int INTEGER
}

CounterSignature ::= CounterSignatureType

CounterSignatureType ::= SEQUENCE {
    signature Signature
}

DataObjectFormat ::= DataObjectFormatType

DataObjectFormatType ::= SEQUENCE {
    objectReference  XSD.AnyURI,
    description      XSD.String OPTIONAL,
    objectIdentifier ObjectIdentifierType OPTIONAL,
    mimeType         XSD.String OPTIONAL,
    encoding         XSD.AnyURI OPTIONAL
}

CommitmentTypeIndication ::= CommitmentTypeIndicationType

CommitmentTypeIndicationType ::= SEQUENCE {
    commitmentTypeId ObjectIdentifierType,
    choice          CHOICE {
	objectReference-list SEQUENCE (SIZE(1..MAX)) OF objectReference 
			     XSD.AnyURI,
	allSignedDataObjects XSD.AnyType
    },
    commitmentTypeQualifiers CommitmentTypeQualifiersListType OPTIONAL
}

CommitmentTypeQualifiersListType ::= SEQUENCE {
    commitmentTypeQualifier-list SEQUENCE OF commitmentTypeQualifier AnyType-1
}

SignatureProductionPlace ::= SignatureProductionPlaceType

SignatureProductionPlaceType ::= SEQUENCE {
    city            XSD.String OPTIONAL,
    stateOrProvince XSD.String OPTIONAL,
    postalCode      XSD.String OPTIONAL,
    countryName     XSD.String OPTIONAL
}

SignerRole ::= SignerRoleType

SignerRoleType ::= SEQUENCE {
    claimedRoles   ClaimedRolesListType OPTIONAL,
    certifiedRoles CertifiedRolesListType OPTIONAL
}

ClaimedRolesListType ::= SEQUENCE {
    claimedRole-list SEQUENCE (SIZE(1..MAX)) OF claimedRole AnyType-1
}

CertifiedRolesListType ::= SEQUENCE {
    certifiedRole-list SEQUENCE (SIZE(1..MAX)) OF certifiedRole 
		       EncapsulatedPKIDataType
}

AllDataObjectsTimeStamp ::= XAdESTimeStampType

IndividualDataObjectsTimeStamp ::= XAdESTimeStampType

SignatureTimeStamp ::= XAdESTimeStampType

CompleteCertificateRefs ::= CompleteCertificateRefsType

CompleteCertificateRefsType ::= SEQUENCE {
    id       XSD.ID OPTIONAL,
    certRefs CertIDListType
}

CompleteRevocationRefs ::= CompleteRevocationRefsType

CompleteRevocationRefsType ::= SEQUENCE {
    id        XSD.ID OPTIONAL,
    cRLRefs   CRLRefsType OPTIONAL,
    oCSPRefs  OCSPRefsType OPTIONAL,
    otherRefs OtherCertStatusRefsType OPTIONAL
}

CRLRefsType ::= SEQUENCE {
    cRLRef-list SEQUENCE (SIZE(1..MAX)) OF cRLRef CRLRefType
}

CRLRefType ::= SEQUENCE {
    digestAlgAndValue DigestAlgAndValueType,
    cRLIdentifier     CRLIdentifierType OPTIONAL
}

CRLIdentifierType ::= SEQUENCE {
    uRI       XSD.AnyURI OPTIONAL,
    issuer    XSD.String,
    issueTime XSD.DateTime,
    number    INTEGER OPTIONAL
}

OCSPRefsType ::= SEQUENCE {
    oCSPRef-list SEQUENCE (SIZE(1..MAX)) OF oCSPRef OCSPRefType
}

OCSPRefType ::= SEQUENCE {
    oCSPIdentifier    OCSPIdentifierType,
    digestAlgAndValue DigestAlgAndValueType OPTIONAL
}

ResponderIDType ::= SEQUENCE {
    choice CHOICE {
	byName XSD.String,
	byKey  OCTET STRING
    }
}

OCSPIdentifierType ::= SEQUENCE {
    uRI         XSD.AnyURI OPTIONAL,
    responderID ResponderIDType,
    producedAt  XSD.DateTime
}

OtherCertStatusRefsType ::= SEQUENCE {
    otherRef-list SEQUENCE (SIZE(1..MAX)) OF otherRef AnyType-1
}

AttributeCertificateRefs ::= CompleteCertificateRefsType

AttributeRevocationRefs ::= CompleteRevocationRefsType

SigAndRefsTimeStamp ::= XAdESTimeStampType

RefsOnlyTimeStamp ::= XAdESTimeStampType

CertificateValues ::= CertificateValuesType

CertificateValuesType ::= SEQUENCE {
    id          XSD.ID OPTIONAL,
    choice-list SEQUENCE OF CHOICE {
	encapsulatedX509Certificate EncapsulatedPKIDataType,
	otherCertificate      AnyType-1
    }
}

RevocationValues ::= RevocationValuesType

RevocationValuesType ::= SEQUENCE {
    id          XSD.ID OPTIONAL,
    cRLValues   CRLValuesType OPTIONAL,
    oCSPValues  OCSPValuesType OPTIONAL,
    otherValues OtherCertStatusValuesType OPTIONAL
}

CRLValuesType ::= SEQUENCE {
    encapsulatedCRLValue-list SEQUENCE (SIZE(1..MAX)) OF encapsulatedCRLValue 
			      EncapsulatedPKIDataType
}

OCSPValuesType ::= SEQUENCE {
    encapsulatedOCSPValue-list SEQUENCE (SIZE(1..MAX)) OF 
			       encapsulatedOCSPValue EncapsulatedPKIDataType
}

OtherCertStatusValuesType ::= SEQUENCE {
    otherValue-list SEQUENCE (SIZE(1..MAX)) OF otherValue AnyType-1
}

AttrAuthoritiesCertValues ::= CertificateValuesType

AttributeRevocationValues ::= RevocationValuesType

ArchiveTimeStamp ::= XAdESTimeStampType

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "http://uri.etsi.org/01903/v1.3.2#"
	PREFIX "xades"
    NAMESPACE ReferenceInfoType.digestMethod, ReferenceInfoType.digestValue, 
	GenericTimeStampType.canonicalizationMethod, 
	XAdESTimeStampType.canonicalizationMethod, 
	OtherTimeStampType.canonicalizationMethod, 
	DigestAlgAndValueType.digestMethod, DigestAlgAndValueType.digestValue,
	SignaturePolicyIdType.transforms, CounterSignatureType.signature
	AS "http://www.w3.org/2000/09/xmldsig#" PREFIX "ds"
    NOT NAMESPACE IdentifierType.qualifier, EncapsulatedPKIDataType.encoding, 
	EncapsulatedPKIDataType.id, IncludeType.uRI, 
	IncludeType.referencedData, ReferenceInfoType.id, 
	ReferenceInfoType.uRI, GenericTimeStampType.id, XAdESTimeStampType.id,
	OtherTimeStampType.id, QualifyingPropertiesType.id, 
	QualifyingPropertiesType.target, SignedPropertiesType.id, 
	UnsignedPropertiesType.id, SignedSignaturePropertiesType.id, 
	SignedDataObjectPropertiesType.id, UnsignedSignaturePropertiesType.id,
	UnsignedDataObjectPropertiesType.id, 
	QualifyingPropertiesReferenceType.id, 
	QualifyingPropertiesReferenceType.uRI, CertIDType.uRI, 
	DataObjectFormatType.objectReference, CompleteCertificateRefsType.id, 
	CompleteRevocationRefsType.id, CRLIdentifierType.uRI, 
	OCSPIdentifierType.uRI, CertificateValuesType.id, 
	RevocationValuesType.id
    NAME AnyType-1 AS "AnyType"
    NAME ObjectIdentifierType.identifier, ObjectIdentifierType.description, 
	ObjectIdentifierType.documentationReferences, 
	IdentifierType.qualifier, 
	DocumentationReferencesType.sequence-list.*.documentationReference, 
	EncapsulatedPKIDataType.encoding, EncapsulatedPKIDataType.id, 
	IncludeType.uRI, ReferenceInfoType.id, ReferenceInfoType.uRI, 
	ReferenceInfoType.digestMethod, ReferenceInfoType.digestValue, 
	GenericTimeStampType.id, 
	GenericTimeStampType.choice.include-list.include, 
	GenericTimeStampType.choice.referenceInfo-list.referenceInfo, 
	GenericTimeStampType.canonicalizationMethod, 
	GenericTimeStampType.choice-list.*.encapsulatedTimeStamp, 
	GenericTimeStampType.choice-list.*.xMLTimeStamp, 
	XAdESTimeStampType.id, XAdESTimeStampType.include-list.include, 
	XAdESTimeStampType.canonicalizationMethod, 
	XAdESTimeStampType.choice-list.*.encapsulatedTimeStamp, 
	XAdESTimeStampType.choice-list.*.xMLTimeStamp, OtherTimeStampType.id, 
	OtherTimeStampType.referenceInfo-list.referenceInfo, 
	OtherTimeStampType.canonicalizationMethod, 
	OtherTimeStampType.choice.encapsulatedTimeStamp, 
	OtherTimeStampType.choice.xMLTimeStamp, QualifyingPropertiesType.id, 
	QualifyingPropertiesType.target, 
	QualifyingPropertiesType.signedProperties, 
	QualifyingPropertiesType.unsignedProperties, SignedPropertiesType.id, 
	SignedPropertiesType.signedSignatureProperties, 
	SignedPropertiesType.signedDataObjectProperties, 
	UnsignedPropertiesType.id, 
	UnsignedPropertiesType.unsignedSignatureProperties, 
	UnsignedPropertiesType.unsignedDataObjectProperties, 
	SignedSignaturePropertiesType.id, 
	SignedSignaturePropertiesType.signingTime, 
	SignedSignaturePropertiesType.signingCertificate, 
	SignedSignaturePropertiesType.signaturePolicyIdentifier, 
	SignedSignaturePropertiesType.signatureProductionPlace, 
	SignedSignaturePropertiesType.signerRole, 
	SignedDataObjectPropertiesType.id, 
	SignedDataObjectPropertiesType.dataObjectFormat-list.dataObjectFormat,
	SignedDataObjectPropertiesType.commitmentTypeIndication-list.commitmentTypeIndication,
	SignedDataObjectPropertiesType.allDataObjectsTimeStamp-list.allDataObjectsTimeStamp,
	SignedDataObjectPropertiesType.individualDataObjectsTimeStamp-list.individualDataObjectsTimeStamp,
	UnsignedSignaturePropertiesType.id, 
	UnsignedSignaturePropertiesType.choice-list.*.counterSignature, 
	UnsignedSignaturePropertiesType.choice-list.*.signatureTimeStamp, 
	UnsignedSignaturePropertiesType.choice-list.*.completeCertificateRefs,
	UnsignedSignaturePropertiesType.choice-list.*.completeRevocationRefs, 
	UnsignedSignaturePropertiesType.choice-list.*.attributeCertificateRefs,
	UnsignedSignaturePropertiesType.choice-list.*.attributeRevocationRefs,
	UnsignedSignaturePropertiesType.choice-list.*.sigAndRefsTimeStamp, 
	UnsignedSignaturePropertiesType.choice-list.*.refsOnlyTimeStamp, 
	UnsignedSignaturePropertiesType.choice-list.*.certificateValues, 
	UnsignedSignaturePropertiesType.choice-list.*.revocationValues, 
	UnsignedSignaturePropertiesType.choice-list.*.attrAuthoritiesCertValues,
	UnsignedSignaturePropertiesType.choice-list.*.attributeRevocationValues,
	UnsignedSignaturePropertiesType.choice-list.*.archiveTimeStamp, 
	UnsignedDataObjectPropertiesType.id, 
	UnsignedDataObjectPropertiesType.unsignedDataObjectProperty-list.unsignedDataObjectProperty,
	QualifyingPropertiesReferenceType.id, 
	QualifyingPropertiesReferenceType.uRI, CertIDListType.cert-list.cert, 
	CertIDType.uRI, CertIDType.certDigest, CertIDType.issuerSerial, 
	DigestAlgAndValueType.digestMethod, DigestAlgAndValueType.digestValue,
	SignaturePolicyIdentifierType.choice.signaturePolicyId, 
	SignaturePolicyIdentifierType.choice.signaturePolicyImplied, 
	SignaturePolicyIdType.sigPolicyId, SignaturePolicyIdType.transforms, 
	SignaturePolicyIdType.sigPolicyHash, 
	SignaturePolicyIdType.sigPolicyQualifiers, 
	SigPolicyQualifiersListType.sigPolicyQualifier-list.sigPolicyQualifier,
	SPUserNoticeType.noticeRef, SPUserNoticeType.explicitText, 
	NoticeReferenceType.organization, NoticeReferenceType.noticeNumbers, 
	CounterSignatureType.signature, DataObjectFormatType.objectReference, 
	DataObjectFormatType.description, 
	DataObjectFormatType.objectIdentifier, DataObjectFormatType.mimeType, 
	DataObjectFormatType.encoding, 
	CommitmentTypeIndicationType.commitmentTypeId, 
	CommitmentTypeIndicationType.choice.objectReference-list.objectReference,
	CommitmentTypeIndicationType.choice.allSignedDataObjects, 
	CommitmentTypeIndicationType.commitmentTypeQualifiers, 
	CommitmentTypeQualifiersListType.commitmentTypeQualifier-list.commitmentTypeQualifier,
	SignatureProductionPlaceType.city, 
	SignatureProductionPlaceType.stateOrProvince, 
	SignatureProductionPlaceType.postalCode, 
	SignatureProductionPlaceType.countryName, SignerRoleType.claimedRoles,
	SignerRoleType.certifiedRoles, 
	ClaimedRolesListType.claimedRole-list.claimedRole, 
	CertifiedRolesListType.certifiedRole-list.certifiedRole, 
	CompleteCertificateRefsType.id, CompleteCertificateRefsType.certRefs, 
	CompleteRevocationRefsType.id, CompleteRevocationRefsType.cRLRefs, 
	CompleteRevocationRefsType.oCSPRefs, 
	CompleteRevocationRefsType.otherRefs, CRLRefsType.cRLRef-list.cRLRef, 
	CRLRefType.digestAlgAndValue, CRLRefType.cRLIdentifier, 
	CRLIdentifierType.uRI, CRLIdentifierType.issuer, 
	CRLIdentifierType.issueTime, CRLIdentifierType.number, 
	OCSPRefsType.oCSPRef-list.oCSPRef, OCSPRefType.oCSPIdentifier, 
	OCSPRefType.digestAlgAndValue, ResponderIDType.choice.byName, 
	ResponderIDType.choice.byKey, OCSPIdentifierType.uRI, 
	OCSPIdentifierType.responderID, OCSPIdentifierType.producedAt, 
	OtherCertStatusRefsType.otherRef-list.otherRef, 
	CertificateValuesType.id, 
	CertificateValuesType.choice-list.*.encapsulatedX509Certificate, 
	CertificateValuesType.choice-list.*.otherCertificate, 
	RevocationValuesType.id, RevocationValuesType.cRLValues, 
	RevocationValuesType.oCSPValues, RevocationValuesType.otherValues, 
	CRLValuesType.encapsulatedCRLValue-list.encapsulatedCRLValue, 
	OCSPValuesType.encapsulatedOCSPValue-list.encapsulatedOCSPValue, 
	OtherCertStatusValuesType.otherValue-list.otherValue AS CAPITALIZED
    ATTRIBUTE IdentifierType.qualifier, EncapsulatedPKIDataType.encoding, 
	EncapsulatedPKIDataType.id, ReferenceInfoType.id, 
	ReferenceInfoType.uRI, GenericTimeStampType.id, XAdESTimeStampType.id,
	OtherTimeStampType.id, QualifyingPropertiesType.id, 
	QualifyingPropertiesType.target, SignedPropertiesType.id, 
	UnsignedPropertiesType.id, SignedSignaturePropertiesType.id, 
	SignedDataObjectPropertiesType.id, UnsignedSignaturePropertiesType.id,
	UnsignedDataObjectPropertiesType.id, CertIDType.uRI, 
	DataObjectFormatType.objectReference, CompleteCertificateRefsType.id, 
	CompleteRevocationRefsType.id, CRLIdentifierType.uRI, 
	OCSPIdentifierType.uRI, CertificateValuesType.id, 
	RevocationValuesType.id
    ATTRIBUTE ALL IN IncludeType, ALL IN QualifyingPropertiesReferenceType
    BASE64 EncapsulatedPKIDataType.base, ResponderIDType.choice.byKey
    EMBED-VALUES AnyType-1
    UNTAGGED SEQUENCE OF, AnyType-1.sequence-list.*, 
	DocumentationReferencesType.sequence-list.*, 
	GenericTimeStampType.choice, GenericTimeStampType.choice-list.*, 
	XAdESTimeStampType.choice-list.*, OtherTimeStampType.choice, 
	UnsignedSignaturePropertiesType.choice-list.*, 
	SignaturePolicyIdentifierType.choice, 
	CommitmentTypeIndicationType.choice, ResponderIDType.choice, 
	CertificateValuesType.choice-list.*
    NOT UNTAGGED AnyType-1.embed-values, AnyType-1.attr
    UNTAGGED base IN ALL
    ANY-ATTRIBUTES AnyType-1.attr
    ANY-ELEMENT AnyType-1.sequence-list.*.elem
    ANY-ELEMENT UnsignedSignaturePropertiesType.choice-list.*.elem
	EXCEPT ABSENT "http://uri.etsi.org/01903/v1.3.2#"
    TEXT QualifierType:ALL AS CAPITALIZED
END
