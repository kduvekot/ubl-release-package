CommonAggregateComponents-2
DEFINITIONS AUTOMATIC TAGS ::=
BEGIN
IMPORTS 
    ID-1, SupplyChainActivityTypeCode, Name-1, Value, AddressTypeCode, 
    AddressFormatCode, Postbox, Floor, Room, StreetName, AdditionalStreetName,
    BlockName, BuildingName, BuildingNumber, InhouseMail, Department, 
    MarkAttention, MarkCare, PlotIdentification, CitySubdivisionName, 
    CityName, PostalZone, CountrySubentity, CountrySubentityCode, Region, 
    District, TimezoneOffset, Line, AircraftID, ChargeIndicator, 
    AllowanceChargeReasonCode, AllowanceChargeReason, MultiplierFactorNumeric,
    PrepaidIndicator, SequenceNumeric, Amount, BaseAmount, AccountingCostCode,
    AccountingCost, PerUnitAmount, Description, EmbeddedDocumentBinaryObject, 
    AuctionConstraintIndicator, JustificationDescription, ProcessDescription, 
    ConditionsDescription, ElectronicDeviceDescription, AuctionURI, 
    AwardingCriteriaTypeCode, WeightNumeric, Weight, CalculationExpression, 
    CalculationExpressionCode, MinimumQuantity, MaximumQuantity, 
    MinimumAmount, MaximumAmount, MinimumImprovementBid, AwardingCriteriaID, 
    AwardingCriteriaDescription, Quantity, WeightingAlgorithmCode, 
    TechnicalCommitteeDescription, LowTendersDescription, BudgetYearNumeric, 
    TotalAmount, EstimatedOverallContractAmount, TaxExclusiveAmount, 
    MonetaryScope, AverageSubsequentContractAmount, CapabilityTypeCode, 
    ValueAmount, ValueQuantity, EvidenceSuppliedID, PrimaryAccountNumberID, 
    NetworkID, CardTypeCode, ValidityStartDate, ExpiryDate, IssuerID, 
    IssueNumberID, CV2ID, CardChipCode, ChipApplicationID, HolderName, 
    ActionCode, LifeCycleStatusCode, ContractSubdivision, Note, 
    OrderableIndicator, OrderableUnit, ContentUnitQuantity, 
    OrderQuantityIncrementNumeric, MinimumOrderQuantity, MaximumOrderQuantity,
    WarrantyInformation, PackLevelCode, UUID, IssueDate, IssueTime, 
    RevisionDate, RevisionTime, VersionID, PreviousVersionID, 
    CertificateTypeCode, CertificateType-1, Remarks, ReferenceID, 
    ApplicationStatusCode, OriginalJobID, PreviousJobID, CodeValue, 
    LastRevisionDate, LastRevisionTime, AgencyID, AgencyName, URI, SchemeURI, 
    LanguageID, NatureCode, CargoTypeCode, CommodityCode, 
    ItemClassificationCode, ChannelCode, Channel, AnnualAverageAmount, 
    TotalTaskAmount, PartyCapacityAmount, CarrierAssignedID, 
    ConsigneeAssignedID, ConsignorAssignedID, FreightForwarderAssignedID, 
    BrokerAssignedID, ContractedCarrierAssignedID, 
    PerformingCarrierAssignedID, SummaryDescription, TotalInvoiceAmount, 
    DeclaredCustomsValueAmount, TariffDescription, TariffCode, 
    InsurancePremiumAmount, GrossWeightMeasure, NetWeightMeasure, 
    NetNetWeightMeasure, ChargeableWeightMeasure, GrossVolumeMeasure, 
    NetVolumeMeasure, LoadingLengthMeasure, HazardousRiskIndicator, 
    AnimalFoodIndicator, HumanFoodIndicator, LivestockIndicator, 
    BulkCargoIndicator, ContainerizedIndicator, GeneralCargoIndicator, 
    SpecialSecurityIndicator, ThirdPartyPayerIndicator, 
    CarrierServiceInstructions, CustomsClearanceServiceInstructions, 
    ForwarderServiceInstructions, SpecialServiceInstructions, SequenceID, 
    ShippingPriorityLevelCode, HandlingCode, HandlingInstructions, 
    Information, TotalGoodsItemQuantity, TotalTransportHandlingUnitQuantity, 
    InsuranceValueAmount, DeclaredForCarriageValueAmount, 
    DeclaredStatisticsValueAmount, FreeOnBoardValueAmount, 
    SpecialInstructions, SplitConsignmentIndicator, DeliveryInstructions, 
    ConsignmentQuantity, ConsolidatableIndicator, HaulageInstructions, 
    LoadingSequenceID, UtilityStatementTypeCode, AverageAmount, MeterNumber, 
    ConsumptionLevelCode, ConsumptionLevel, ParentDocumentLineReferenceID, 
    InvoicedQuantity, LineExtensionAmount, SubscriberID, 
    SubscriberTypeIdentifier, SubscriberTypeCode, TotalDeliveredQuantity, 
    ConsumptionType-1, ConsumptionTypeCode, TotalConsumedQuantity, 
    BasicConsumedQuantity, ResidentOccupantsNumeric, ConsumersEnergyLevelCode,
    ConsumersEnergyLevel, ResidenceType, ResidenceTypeCode, HeatingType, 
    HeatingTypeCode, ConsumptionReportID, Telephone, Telefax, ElectronicMail, 
    NominationDate, NominationTime, ContractTypeCode, ContractType-1, 
    ExecutionRequirementCode, OptionsDescription, MinimumNumberNumeric, 
    MaximumNumberNumeric, ContractingPartyTypeCode, ActivityCode, 
    BuyerProfileURI, CorporateRegistrationTypeCode, CorrectionType-1, 
    CorrectionTypeCode, GasPressureQuantity, 
    ActualTemperatureReductionQuantity, NormalTemperatureReductionQuantity, 
    DifferenceTemperatureReductionQuantity, CorrectionUnitAmount, 
    ConsumptionEnergyQuantity, ConsumptionWaterQuantity, CorrectionAmount, 
    IdentificationCode, AccountID, CreditedQuantity, TaxPointDate, 
    PaymentPurposeCode, FreeOfChargeIndicator, CustomerAssignedAccountID, 
    SupplierAssignedAccountID, AdditionalAccountID, DebitedQuantity, 
    DeclarationTypeCode, ActualDeliveryDate, ActualDeliveryTime, 
    LatestDeliveryDate, LatestDeliveryTime, ReleaseID, TrackingID, 
    SpecialTerms, LossRiskResponsibilityCode, LossRisk, BatchQuantity, 
    ConsumerUnitQuantity, Percent, RequestedDespatchDate, 
    RequestedDespatchTime, EstimatedDespatchDate, EstimatedDespatchTime, 
    ActualDespatchDate, ActualDespatchTime, GuaranteedDespatchDate, 
    GuaranteedDespatchTime, Instructions, LineStatusCode, DeliveredQuantity, 
    BackorderQuantity, BackorderReason, OutstandingQuantity, 
    OutstandingReason, OversupplyQuantity, AttributeID, Measure, 
    MinimumMeasure, MaximumMeasure, PrintQualifier, MaximumCopiesNumeric, 
    CopyIndicator, DocumentTypeCode, DocumentType, XPath, LocaleCode, 
    DocumentStatusCode, DocumentDescription, Duty-1, DutyCode, 
    LimitationDescription, ExpectedQuantity, DocumentID, ApprovalStatus, 
    RoleCode, TaxEnergyAmount, TaxEnergyOnAccountAmount, 
    TaxEnergyBalanceAmount, EnvironmentalEmissionTypeCode, ValueMeasure, 
    EvaluationCriteriaTypeCode, ThresholdAmount, ThresholdQuantity, 
    ExpressionCode, IdentificationID, OccurrenceDate, OccurrenceTime, 
    TypeCode, CompletionIndicator, Comment, LineNumberNumeric, 
    ConsumerIncentiveTacticTypeCode, DisplayTacticTypeCode, 
    FeatureTacticTypeCode, TradeItemPackingLabelingTypeCode, EvidenceTypeCode,
    ThresholdValueComparisonCode, ExceptionStatusCode, 
    CollaborationPriorityCode, ExceptionResolutionCode, 
    PerformanceMetricTypeCode, ResolutionCode, ComparedValueMeasure, 
    SourceValueMeasure, VarianceQuantity, SourceCurrencyCode, 
    SourceCurrencyBaseRate, TargetCurrencyCode, TargetCurrencyBaseRate, 
    ExchangeMarketID, CalculationRate, MathematicOperatorCode, Date-1, 
    DocumentHash, HashAlgorithmMethod, ExpiryTime, MimeCode, FormatCode, 
    EncodingCode, CharacterSetCode, FileName, AliasName, AccountTypeCode, 
    AccountFormatCode, CurrencyCode, PaymentNote, GuaranteeTypeCode, 
    LiabilityAmount, AmountRate, ForecastPurposeCode, ForecastTypeCode, 
    DataSourceCode, ComparisonDataCode, ComparisonForecastIssueTime, 
    ComparisonForecastIssueDate, ComparisonDataSourceCode, 
    TimeDeltaDaysQuantity, FrozenDocumentIndicator, RevisedForecastLineID, 
    SourceForecastIssueDate, SourceForecastIssueTime, AdjustmentReasonCode, 
    ExpectedOperatorQuantity, MaximumOperatorQuantity, Justification, 
    Frequency, SequenceNumberID, PreferenceCriterionCode, RequiredCustomsID, 
    CustomsStatusCode, CustomsTariffQuantity, 
    CustomsImportClassifiedIndicator, ChargeableQuantity, ReturnableQuantity, 
    TransportEmergencyCardCode, PackingCriteriaCode, HazardousRegulationCode, 
    InhalationToxicityZoneCode, TransportAuthorizationCode, PlacardNotation, 
    PlacardEndorsement, AdditionalInformation, UNDGCode, 
    EmergencyProceduresCode, MedicalFirstAidGuideCode, TechnicalName, 
    CategoryName, HazardousCategoryCode, UpperOrangeHazardPlacardID, 
    LowerOrangeHazardPlacardID, MarkingID, HazardClassID, 
    ImmobilizationCertificateID, SecurityID, FaceValueAmount, 
    MarketValueAmount, SharesNumberQuantity, InventoryValueAmount, 
    AvailabilityDate, AvailabilityStatusCode, PackQuantity, PackSizeNumeric, 
    CatalogueIndicator, Keyword, BrandName, ModelName, PriceAmount, 
    ExtendedID, TimeFrequencyCode, ProductTraceID, ManufactureDate, 
    ManufactureTime, BestBeforeDate, RegistrationID, SerialID, 
    LeadTimeMeasure, TradingRestrictions, FrozenPeriodDaysNumeric, 
    MinimumInventoryQuantity, MultipleOrderQuantity, OrderIntervalDaysNumeric,
    ReplenishmentOwnerDescription, TargetServicePercent, 
    TargetInventoryQuantity, NameCode, TestMethod, ValueQualifier, 
    ImportanceCode, ListValue, MinimumValue, MaximumValue, SalesOrderID, 
    TotalTaxAmount, MinimumBackorderQuantity, MaximumBackorderQuantity, 
    InspectionMethodCode, PartialDeliveryIndicator, BackOrderAllowedIndicator,
    LineID, Conditions, LocationTypeCode, InformationURI, 
    CoordinateSystemCode, LatitudeDegreesMeasure, LatitudeMinutesMeasure, 
    LatitudeDirectionCode, LongitudeDegreesMeasure, LongitudeMinutesMeasure, 
    LongitudeDirectionCode, AltitudeMeasure, LotNumberID, VesselID, 
    VesselName, MeterName, MeterConstant, MeterConstantCode, 
    MeterReadingType-1, MeterReadingTypeCode, PreviousMeterReadingDate, 
    PreviousMeterQuantity, LatestMeterReadingDate, LatestMeterQuantity, 
    MeterReadingMethod, MeterReadingMethodCode, MeterReadingComments, 
    MiscellaneousEventTypeCode, TaxInclusiveAmount, AllowanceTotalAmount, 
    ChargeTotalAmount, PrepaidAmount, PayableRoundingAmount, PayableAmount, 
    PayableAlternativeAmount, NotificationTypeCode, EstimatedConsumedQuantity,
    SubstitutionStatusCode, SalesOrderLineID, CustomerReference, 
    OrderTypeCode, ReturnableMaterialIndicator, PackageLevelCode, 
    PackagingTypeCode, PackingMaterial, TraceID, MarkCareIndicator, 
    MarkAttentionIndicator, WebsiteURI, LogoReferenceID, EndpointID, 
    IndustryClassificationCode, RegistrationName, CompanyID, RegistrationDate,
    RegistrationExpirationDate, CompanyLegalFormCode, 
    SoleProprietorshipIndicator, CompanyLiquidationStatusCode, 
    CorporateStockAmount, FullyPaidSharesIndicator, TaxLevelCode, 
    ExemptionReasonCode, ExemptionReason, PaidAmount, ReceivedDate, PaidDate, 
    PaidTime, InstructionID, MandateTypeCode, Clause, ClauseCode, 
    MaximumPaymentInstructionsNumeric, MaximumPaidAmount, SignatureID, 
    PaymentMeansCode, PaymentDueDate, PaymentChannelCode, InstructionNote, 
    PaymentID, PaymentMeansID, PrepaidPaymentReferenceID, ReferenceEventCode, 
    SettlementDiscountPercent, PenaltySurchargePercent, PaymentPercent, 
    SettlementDiscountAmount, PenaltyAmount, PaymentTermsDetailsURI, 
    InstallmentDueDate, InvoicingPartyReference, PerformanceValueQuantity, 
    StartDate, StartTime, EndDate, EndTime, DurationMeasure, DescriptionCode, 
    FirstName, FamilyName, Title, MiddleName, NameSuffix, JobTitle, 
    NationalityID, GenderCode, BirthDate, OrganizationDepartment, 
    PositionCode, ActualPickupDate, ActualPickupTime, EarliestPickupDate, 
    EarliestPickupTime, LatestPickupDate, LatestPickupTime, BaseQuantity, 
    PriceChangeReason, PriceTypeCode, PriceType-1, OrderableUnitFactorRate, 
    StatusCode, PreviousCancellationReasonCode, ProcessReasonCode, 
    ProcessReason, ProcurementTypeCode, ProcurementSubTypeCode, 
    QualityControlCode, RequiredFeeAmount, FeeDescription, 
    RequestedDeliveryDate, EstimatedOverallContractQuantity, 
    PromotionalEventTypeCode, SubmissionDate, FirstShipmentAvailibilityDate, 
    LatestProposalAcceptanceDate, SpecificationID, AdmissionCode, 
    ProcurementProjectLotID, ExclusionReason, Resolution, ResolutionDate, 
    ResolutionTime, ParticipationPercent, PersonalSituation, 
    OperatingYearsQuantity, EmployeeQuantity, 
    BusinessClassificationEvidenceID, BusinessIdentityEvidenceID, 
    RequestForQuotationLineID, TrainID, RailCarID, ReceivedQuantity, 
    ShortQuantity, ShortageActionCode, RejectedQuantity, RejectReasonCode, 
    RejectReason, RejectActionCode, QuantityDiscrepancyCode, 
    TimingComplaintCode, TimingComplaint, LegalReference, OntologyURI, 
    BalanceBroughtForwardIndicator, DebitLineAmount, CreditLineAmount, 
    BalanceAmount, OptionalLineItemIndicator, PrivacyCode, 
    SecurityClassificationCode, MaximumTaxExclusiveAmount, 
    MaximumTaxInclusiveAmount, ResponseCode, EffectiveDate, EffectiveTime, 
    ValidatorID, ValidationResultCode, ValidationDate, ValidationTime, 
    ValidateProcess, ValidateTool, ValidateToolVersion, LicensePlateID, 
    Extension, TransportModeCode, ServiceTypeCode, ServiceType, 
    PartecipationPercent, TransportMeansTypeCode, TransitDirectionCode, 
    PreCarriageIndicator, OnCarriageIndicator, EstimatedDeliveryDate, 
    EstimatedDeliveryTime, RequiredDeliveryDate, RequiredDeliveryTime, 
    SuccessiveSequenceID, DemurrageInstructions, CanonicalizationMethod-1, 
    SignatureMethod-1, ConditionCode, ReferenceDate, ReferenceTime, 
    StatusReasonCode, StatusReason, Text, IndicationIndicator, 
    ConditionValueMeasure, ReliabilityPercent, LocationID, Location-1, Rate, 
    UnknownPriceIndicator, ConsumptionID, SpecificationTypeCode, 
    TotalMeteredQuantity, DataSendingCapability, BaseUnitMeasure, 
    TaxExemptionReasonCode, TaxExemptionReason, TierRange, TierRatePercent, 
    TaxTypeCode, TaxableAmount, TaxAmount, CalculationSequenceNumeric, 
    TransactionCurrencyTaxAmount, RoundingAmount, TaxEvidenceIndicator, 
    TaxIncludedIndicator, CallDate, CallTime, ServiceNumberCalled, 
    TelecommunicationsServiceCategory, TelecommunicationsServiceCategoryCode, 
    MovieTitle, RoamingPartnerName, PayPerView, TelecommunicationsServiceCall,
    TelecommunicationsServiceCallCode, CallBaseAmount, CallExtensionAmount, 
    TelecommunicationsSupplyType-1, TelecommunicationsSupplyTypeCode, 
    PhoneNumber, TenderEnvelopeID, TenderEnvelopeTypeCode, OpenTenderID, 
    TenderResultCode, AdvertisementAmount, AwardDate, AwardTime, 
    ReceivedTenderQuantity, LowerTenderAmount, HigherTenderAmount, VariantID, 
    FeeAmount, InterestedProcurementLotsID, LegalForm, 
    TendererRequirementTypeCode, OriginalContractingSystemID, 
    NegotiationDescription, ProcedureCode, UrgencyCode, ExpenseCode, 
    PartPresentationCode, ContractingSystemCode, SubmissionMethodCode, 
    CandidateReductionConstraintIndicator, 
    GovernmentAgreementConstraintIndicator, AwardingMethodTypeCode, 
    PriceEvaluationCode, MaximumVariantQuantity, VariantConstraintIndicator, 
    AcceptedVariantsDescription, PriceRevisionFormulaDescription, 
    FundingProgramCode, FundingProgram, MaximumAdvertisementAmount, 
    PaymentFrequencyCode, EconomicOperatorRegistryURI, PenaltyClauses, 
    RequiredCurriculaIndicator, FinancingInstrumentCode, Reference-1, 
    ReferencedConsignmentID, TransportEquipmentTypeCode, ProviderTypeCode, 
    OwnerTypeCode, SizeTypeCode, DispositionCode, FullnessIndicationCode, 
    RefrigerationOnIndicator, ReturnabilityIndicator, LegalStatusIndicator, 
    AirFlowPercent, HumidityPercent, AnimalFoodApprovedIndicator, 
    HumanFoodApprovedIndicator, DangerousGoodsApprovedIndicator, 
    RefrigeratedIndicator, Characteristics, DamageRemarks, 
    SpecialTransportRequirments, TareWeightMeasure, TrackingDeviceCode, 
    PowerIndicator, SealIssuerTypeCode, Condition, SealStatusCode, 
    SealingPartyType, TransportEventTypeCode, TransportUserSpecialTerms, 
    TransportServiceProviderSpecialTerms, ChangeConditions, 
    TransportHandlingUnitTypeCode, TotalPackageQuantity, ShippingMarks, 
    JourneyID, RegistrationNationalityID, RegistrationNationality, 
    DirectionCode, TradeServiceCode, TimeDeviationIndicator, 
    ConditionDeviationIndicator, TransportExecutionPlanReferenceID, 
    TransportServiceCode, TariffClassCode, Priority, FreightRateClassCode, 
    TransportationServiceDescription, TransportationServiceDetailsURI, 
    TimeAmount, SubscriberIDType, SubscriberIDTypeCode, CurrentChargeType, 
    CurrentChargeTypeCode, OneTimeChargeType, OneTimeChargeTypeCode, Password,
    Login
    FROM CommonBasicComponents-2;

AcceptanceTransportEvent ::= TransportEventType

AccessoryRelatedItem ::= RelatedItemType

AccountingContact ::= ContactType

AccountingCustomerParty ::= CustomerPartyType

AccountingSupplierParty ::= SupplierPartyType

ActivityDataLine ::= ActivityDataLineType

ActivityFinalLocation ::= LocationType

ActivityOriginLocation ::= LocationType

ActivityPeriod ::= PeriodType

ActivityProperty ::= ActivityPropertyType

ActualArrivalTransportEvent ::= TransportEventType

ActualDepartureTransportEvent ::= TransportEventType

ActualPackage ::= PackageType

ActualPickupTransportEvent ::= TransportEventType

AdditionalDocumentReference ::= DocumentReferenceType

AdditionalDocumentResponse ::= DocumentResponseType

AdditionalInformationParty ::= PartyType

AdditionalItemIdentification ::= ItemIdentificationType

AdditionalItemProperty ::= ItemPropertyType

AdditionalQualifyingParty ::= QualifyingPartyType

AdditionalTemperature ::= TemperatureType

AdditionalTransportationService ::= TransportationServiceType

Address ::= AddressType

AddressLine ::= AddressLineType

AgentParty ::= PartyType

AirTransport ::= AirTransportType

AllowanceCharge ::= AllowanceChargeType

AllowedSubcontractTerms ::= SubcontractTermsType

AlternativeConditionPrice ::= PriceType

AlternativeDeliveryLocation ::= LocationType

AlternativeLineItem ::= LineItemType

AnticipatedMonetaryTotal ::= MonetaryTotalType

AppealInformationParty ::= PartyType

AppealReceiverParty ::= PartyType

AppealTerms ::= AppealTermsType

ApplicableAddress ::= AddressType

ApplicablePeriod ::= PeriodType

ApplicableRegulation ::= RegulationType

ApplicableTaxCategory ::= TaxCategoryType

ApplicableTerritoryAddress ::= AddressType

ApplicableTransportMeans ::= TransportMeansType

ArrivalTransportLocation ::= TransportLocationType

AtLocation ::= LocationType

AttachedTransportEquipment ::= TransportEquipmentType

Attachment ::= AttachmentType

AuctionTerms ::= AuctionTermsType

AvailabilityTransportEvent ::= TransportEventType

AwardedTenderedProject ::= TenderedProjectType

AwardingCriteria ::= AwardingCriteriaType

AwardingCriteriaResponse ::= AwardingCriteriaResponseType

AwardingTerms ::= AwardingTermsType

BeneficiaryParty ::= PartyType

BillOfLadingHolderParty ::= PartyType

BillingReference ::= BillingReferenceType

BillingReferenceLine ::= BillingReferenceLineType

BonusMonetaryTotal ::= MonetaryTotalType

BonusPaymentTerms ::= PaymentTermsType

Branch ::= BranchType

BudgetAccount ::= BudgetAccountType

BudgetAccountLine ::= BudgetAccountLineType

BudgetAmount ::= BudgetAmountType

BusinessClassificationScheme ::= ClassificationSchemeType

BuyerContact ::= ContactType

BuyerCustomerParty ::= CustomerPartyType

BuyerProposedSubstituteLineItem ::= LineItemType

BuyersItemIdentification ::= ItemIdentificationType

CallDuty ::= DutyType

CallForTenderDocumentReference ::= DocumentReferenceType

Capability ::= CapabilityType

CardAccount ::= CardAccountType

CarrierParty ::= PartyType

CarryingPackage ::= PackageType

CarryingTransportEquipment ::= TransportEquipmentType

CarryingTransportMeans ::= TransportMeansType

CatalogueDocumentReference ::= DocumentReferenceType

CatalogueItemIdentification ::= ItemIdentificationType

CatalogueItemSpecificationUpdateLine ::= 
    CatalogueItemSpecificationUpdateLineType

CatalogueLine ::= CatalogueLineType

CatalogueLineReference ::= LineReferenceType

CataloguePricingUpdateLine ::= CataloguePricingUpdateLineType

CatalogueReference ::= CatalogueReferenceType

CatalogueRequestLine ::= CatalogueRequestLineType

CategorizesClassificationCategory ::= ClassificationCategoryType

Certificate ::= CertificateType

CertificateOfOriginApplication ::= CertificateOfOriginApplicationType

ClassificationCategory ::= ClassificationCategoryType

ClassificationScheme ::= ClassificationSchemeType

ClassifiedTaxCategory ::= TaxCategoryType

CollectPaymentTerms ::= PaymentTermsType

CommissionMonetaryTotal ::= MonetaryTotalType

CommissionPaymentTerms ::= PaymentTermsType

CommodityClassification ::= CommodityClassificationType

Communication ::= CommunicationType

ComplementaryRelatedItem ::= RelatedItemType

CompletedTask ::= CompletedTaskType

ComponentRelatedItem ::= RelatedItemType

ConsigneeParty ::= PartyType

Consignment ::= ConsignmentType

ConsignorParty ::= PartyType

ConsolidatedShipment ::= ShipmentType

ConstitutionPeriod ::= PeriodType

Consumption ::= ConsumptionType

ConsumptionAverage ::= ConsumptionAverageType

ConsumptionHistory ::= ConsumptionHistoryType

ConsumptionLine ::= ConsumptionLineType

ConsumptionPoint ::= ConsumptionPointType

ConsumptionReport ::= ConsumptionReportType

ConsumptionReportReference ::= ConsumptionReportReferenceType

Contact ::= ContactType

ContactParty ::= PartyType

ContainedGoodsItem ::= GoodsItemType

ContainedInTransportEquipment ::= TransportEquipmentType

ContainedPackage ::= PackageType

ContainingPackage ::= PackageType

ContainingTransportEquipment ::= TransportEquipmentType

Contract ::= ContractType

ContractAcceptancePeriod ::= PeriodType

ContractDocumentReference ::= DocumentReferenceType

ContractExecutionRequirement ::= ContractExecutionRequirementType

ContractExtension ::= ContractExtensionType

ContractFormalizationPeriod ::= PeriodType

ContractResponsibleParty ::= PartyType

ContractingParty ::= ContractingPartyType

ContractorCustomerParty ::= CustomerPartyType

ContractualDelivery ::= DeliveryType

ContractualDocumentReference ::= DocumentReferenceType

CorporateRegistrationScheme ::= CorporateRegistrationSchemeType

Correction ::= CorrectionType

Country ::= CountryType

CreditAccount ::= CreditAccountType

CreditNoteDocumentReference ::= DocumentReferenceType

CreditNoteLine ::= CreditNoteLineType

CurrentStatus ::= StatusType

CustomerParty ::= CustomerPartyType

CustomsAgentParty ::= PartyType

DebitNoteDocumentReference ::= DocumentReferenceType

DebitNoteLine ::= DebitNoteLineType

Declaration ::= DeclarationType

DefaultLanguage ::= LanguageType

DeletedCatalogueReference ::= CatalogueReferenceType

Delivery ::= DeliveryType

DeliveryAddress ::= AddressType

DeliveryContact ::= ContactType

DeliveryCustomerParty ::= CustomerPartyType

DeliveryLocation ::= LocationType

DeliveryParty ::= PartyType

DeliveryPeriod ::= PeriodType

DeliveryTerms ::= DeliveryTermsType

DeliveryTransportEvent ::= TransportEventType

DeliveryUnit ::= DeliveryUnitType

DepartureTransportLocation ::= TransportLocationType

DependentLineReference ::= LineReferenceType

DependentPriceReference ::= DependentPriceReferenceType

Despatch ::= DespatchType

DespatchAddress ::= AddressType

DespatchContact ::= ContactType

DespatchDocumentReference ::= DocumentReferenceType

DespatchLine ::= DespatchLineType

DespatchLineReference ::= LineReferenceType

DespatchLocation ::= LocationType

DespatchParty ::= PartyType

DespatchPeriod ::= PeriodType

DespatchSupplierParty ::= SupplierPartyType

DestinationCountry ::= CountryType

DigitalSignatureAttachment ::= AttachmentType

Dimension ::= DimensionType

DisbursementPaymentTerms ::= PaymentTermsType

DischargeTransportEvent ::= TransportEventType

DiscrepancyResponse ::= ResponseType

DocumentAvailabilityPeriod ::= PeriodType

DocumentDistribution ::= DocumentDistributionType

DocumentProviderParty ::= PartyType

DocumentReference ::= DocumentReferenceType

DocumentResponse ::= DocumentResponseType

DocumentTenderRequirement ::= TenderRequirementType

DropoffTransportEvent ::= TransportEventType

DurationPeriod ::= PeriodType

Duty ::= DutyType

EconomicOperatorShortList ::= EconomicOperatorShortListType

EffectivePeriod ::= PeriodType

EmbassyEndorsement ::= EndorsementType

EmergencyTemperature ::= TemperatureType

EmploymentLegislationDocumentReference ::= DocumentReferenceType

Endorsement ::= EndorsementType

EndorserParty ::= EndorserPartyType

EnergyTaxReport ::= EnergyTaxReportType

EnergyWaterCorrection ::= CorrectionType

EnergyWaterSupply ::= EnergyWaterSupplyType

EnvironmentalEmission ::= EnvironmentalEmissionType

EnvironmentalLegislationDocumentReference ::= DocumentReferenceType

EstimatedArrivalPeriod ::= PeriodType

EstimatedDeliveryPeriod ::= PeriodType

EstimatedDeparturePeriod ::= PeriodType

EstimatedDespatchPeriod ::= PeriodType

EvaluationCriteria ::= EvaluationCriteriaType

Event ::= EventType

EventComment ::= EventCommentType

EventLineItem ::= EventLineItemType

EventTactic ::= EventTacticType

EventTacticEnumeration ::= EventTacticEnumerationType

Evidence ::= EvidenceType

EvidenceIssuingParty ::= PartyType

ExaminationTransportEvent ::= TransportEventType

ExceptionCriteriaLine ::= ExceptionCriteriaLineType

ExceptionNotificationLine ::= ExceptionNotificationLineType

ExceptionObservationPeriod ::= PeriodType

ExchangeRate ::= ExchangeRateType

ExportCountry ::= CountryType

ExportationTransportEvent ::= TransportEventType

ExporterParty ::= PartyType

ExternalReference ::= ExternalReferenceType

ExtraAllowanceCharge ::= AllowanceChargeType

FinalDeliveryParty ::= PartyType

FinalDeliveryTransportationService ::= TransportationServiceType

FinalDestinationCountry ::= CountryType

FinalFinancialGuarantee ::= FinancialGuaranteeType

FinancialAccount ::= FinancialAccountType

FinancialCapability ::= CapabilityType

FinancialEvaluationCriteria ::= EvaluationCriteriaType

FinancialGuarantee ::= FinancialGuaranteeType

FinancialInstitution ::= FinancialInstitutionType

FinancialInstitutionBranch ::= BranchType

FinancingFinancialAccount ::= FinancialAccountType

FinancingParty ::= PartyType

FirstArrivalPortLocation ::= LocationType

FiscalLegislationDocumentReference ::= DocumentReferenceType

FlashpointTemperature ::= TemperatureType

FloorSpaceMeasurementDimension ::= DimensionType

ForecastException ::= ForecastExceptionType

ForecastExceptionCriteriaLine ::= ForecastExceptionCriteriaLineType

ForecastLine ::= ForecastLineType

ForecastPeriod ::= PeriodType

ForecastRevisionLine ::= ForecastRevisionLineType

ForeignExchangeContract ::= ContractType

FrameworkAgreement ::= FrameworkAgreementType

FreightAllowanceCharge ::= AllowanceChargeType

FreightForwarderParty ::= PartyType

FrequencyPeriod ::= PeriodType

FromLocation ::= LocationType

GoodsItem ::= GoodsItemType

GoodsItemContainer ::= GoodsItemContainerType

GuaranteeDocumentReference ::= DocumentReferenceType

GuarantorParty ::= PartyType

GuidanceDocumentReference ::= DocumentReferenceType

HandlingTransportEvent ::= TransportEventType

HandlingUnitDespatchLine ::= DespatchLineType

HaulageTradingTerms ::= TradingTermsType

HazardousGoodsTransit ::= HazardousGoodsTransitType

HazardousItem ::= HazardousItemType

HazardousItemNotificationParty ::= PartyType

HeadParty ::= PartyType

IdentityDocumentReference ::= DocumentReferenceType

ImmobilizedSecurity ::= ImmobilizedSecurityType

ImporterParty ::= PartyType

InformationContentProviderParty ::= PartyType

InstructionForReturnsLine ::= InstructionForReturnsLineType

InsuranceEndorsement ::= EndorsementType

InsuranceParty ::= PartyType

InterestedParty ::= PartyType

IntermediateTransportLocation ::= TransportLocationType

InventoryPeriod ::= PeriodType

InventoryReportLine ::= InventoryReportLineType

InventoryReportingParty ::= PartyType

InvitationSubmissionPeriod ::= PeriodType

InvoiceDocumentReference ::= DocumentReferenceType

InvoiceLine ::= InvoiceLineType

InvoicePeriod ::= PeriodType

IssuerEndorsement ::= EndorsementType

IssuerParty ::= PartyType

IssuingCountry ::= CountryType

Item ::= ItemType

ItemComparison ::= ItemComparisonType

ItemIdentification ::= ItemIdentificationType

ItemInformationRequestLine ::= ItemInformationRequestLineType

ItemInstance ::= ItemInstanceType

ItemLocationQuantity ::= ItemLocationQuantityType

ItemManagementProfile ::= ItemManagementProfileType

ItemProperty ::= ItemPropertyType

ItemPropertyGroup ::= ItemPropertyGroupType

ItemPropertyRange ::= ItemPropertyRangeType

ItemSpecificationDocumentReference ::= DocumentReferenceType

JurisdictionRegionAddress ::= AddressType

KeywordItemProperty ::= ItemPropertyType

Language-1 ::= LanguageType

LastExitPortLocation ::= LocationType

LegalDocumentReference ::= DocumentReferenceType

LegalMonetaryTotal ::= MonetaryTotalType

LineItem ::= LineItemType

LineReference ::= LineReferenceType

LineResponse ::= LineResponseType

LineValidityPeriod ::= PeriodType

LoadingLocation ::= LocationType

LoadingPortLocation ::= LocationType

LoadingProofParty ::= PartyType

LoadingTransportEvent ::= TransportEventType

Location ::= LocationType

LocationAddress ::= AddressType

LocationCoordinate ::= LocationCoordinateType

LogisticsOperatorParty ::= PartyType

LotIdentification ::= LotIdentificationType

MainCarriageShipmentStage ::= ShipmentStageType

MainOnAccountPayment ::= OnAccountPaymentType

MainPeriod ::= PeriodType

MainQualifyingParty ::= QualifyingPartyType

MainTransportationService ::= TransportationServiceType

MandateDocumentReference ::= DocumentReferenceType

ManufacturerParty ::= PartyType

ManufacturersItemIdentification ::= ItemIdentificationType

MaritimeTransport ::= MaritimeTransportType

MaximumDeliveryUnit ::= DeliveryUnitType

MaximumTemperature ::= TemperatureType

MeasurementDimension ::= DimensionType

MediationParty ::= PartyType

Meter ::= MeterType

MeterProperty ::= MeterPropertyType

MeterReading ::= MeterReadingType

MinimumDeliveryUnit ::= DeliveryUnitType

MinimumTemperature ::= TemperatureType

MinutesDocumentReference ::= DocumentReferenceType

MiscellaneousEvent ::= MiscellaneousEventType

MonetaryTotal ::= MonetaryTotalType

MortgageHolderParty ::= PartyType

NominationPeriod ::= PeriodType

NotaryParty ::= PartyType

NoticeDocumentReference ::= DocumentReferenceType

NotificationRequirement ::= NotificationRequirementType

NotifyParty ::= PartyType

OccurenceLocation ::= LocationType

OfferedItemLocationQuantity ::= ItemLocationQuantityType

OnAccountPayment ::= OnAccountPaymentType

OnCarriageShipmentStage ::= ShipmentStageType

OpenTenderEvent ::= EventType

OperatingParty ::= PartyType

OperatorParty ::= PartyType

OptionValidityPeriod ::= PeriodType

OptionalTakeoverTransportEvent ::= TransportEventType

OrderDocumentReference ::= DocumentReferenceType

OrderLine ::= OrderLineType

OrderLineReference ::= OrderLineReferenceType

OrderReference ::= OrderReferenceType

OrderedShipment ::= OrderedShipmentType

OriginAddress ::= AddressType

OriginCountry ::= CountryType

OriginalDepartureCountry ::= CountryType

OriginalDespatchParty ::= PartyType

OriginalDespatchTransportationService ::= TransportationServiceType

OriginalDocumentReference ::= DocumentReferenceType

OriginalItemLocationQuantity ::= ItemLocationQuantityType

OriginatorCustomerParty ::= CustomerPartyType

OriginatorDocumentReference ::= DocumentReferenceType

OriginatorParty ::= PartyType

OtherCommunication ::= CommunicationType

OwnerParty ::= PartyType

Package ::= PackageType

PackagedTransportHandlingUnit ::= TransportHandlingUnitType

PalletSpaceMeasurementDimension ::= DimensionType

ParentDocumentLineReference ::= LineReferenceType

ParentDocumentReference ::= DocumentReferenceType

ParticipatingLocationsLocation ::= LocationType

ParticipationRequestReceptionPeriod ::= PeriodType

Party ::= PartyType

PartyIdentification ::= PartyIdentificationType

PartyLegalEntity ::= PartyLegalEntityType

PartyName ::= PartyNameType

PartyTaxScheme ::= PartyTaxSchemeType

PayeeFinancialAccount ::= FinancialAccountType

PayeeParty ::= PartyType

PayerFinancialAccount ::= FinancialAccountType

PayerParty ::= PartyType

Payment ::= PaymentType

PaymentAlternativeExchangeRate ::= ExchangeRateType

PaymentExchangeRate ::= ExchangeRateType

PaymentMandate ::= PaymentMandateType

PaymentMeans ::= PaymentMeansType

PaymentReversalPeriod ::= PeriodType

PaymentTerms ::= PaymentTermsType

PenaltyMonetaryTotal ::= MonetaryTotalType

PenaltyPaymentTerms ::= PaymentTermsType

PenaltyPeriod ::= PeriodType

PerformanceDataLine ::= PerformanceDataLineType

PerformingCarrierParty ::= PartyType

Period ::= PeriodType

Person ::= PersonType

PhysicalAttribute ::= PhysicalAttributeType

PhysicalLocation ::= LocationType

Pickup ::= PickupType

PickupLocation ::= LocationType

PickupParty ::= PartyType

PickupTransportEvent ::= TransportEventType

PlannedArrivalPeriod ::= PeriodType

PlannedDeparturePeriod ::= PeriodType

PlannedPeriod ::= PeriodType

PositioningTransportEvent ::= TransportEventType

PostEventPeriod ::= PeriodType

PostalAddress ::= AddressType

PowerOfAttorney ::= PowerOfAttorneyType

PreCarriageShipmentStage ::= ShipmentStageType

PreEventPeriod ::= PeriodType

PreSelectedParty ::= PartyType

PrepaidPayment ::= PaymentType

PrepaidPaymentTerms ::= PaymentTermsType

PreparationParty ::= PartyType

PresentationPeriod ::= PeriodType

PreviousDocumentReference ::= DocumentReferenceType

PreviousPriceList ::= PriceListType

Price ::= PriceType

PriceList ::= PriceListType

PriceMonetaryTotal ::= MonetaryTotalType

PricingExchangeRate ::= ExchangeRateType

PricingReference ::= PricingReferenceType

ProcessJustification ::= ProcessJustificationType

ProcurementLegislationDocumentReference ::= DocumentReferenceType

ProcurementProject ::= ProcurementProjectType

ProcurementProjectLot ::= ProcurementProjectLotType

PromisedDeliveryPeriod ::= PeriodType

PromotionalEvent ::= PromotionalEventType

PromotionalEventLineItem ::= PromotionalEventLineItemType

PromotionalSpecification ::= PromotionalSpecificationType

ProviderParty ::= PartyType

QualificationResolution ::= QualificationResolutionType

QualifyingParty ::= QualifyingPartyType

QuarantineTransportEvent ::= TransportEventType

QuotationDocumentReference ::= DocumentReferenceType

QuotationLine ::= QuotationLineType

QuotationLineReference ::= LineReferenceType

QuotedMonetaryTotal ::= MonetaryTotalType

RailTransport ::= RailTransportType

RangeDimension ::= DimensionType

RealizedLocation ::= LocationType

ReceiptDocumentReference ::= DocumentReferenceType

ReceiptLine ::= ReceiptLineType

ReceiptLineReference ::= LineReferenceType

ReceiptTransportEvent ::= TransportEventType

ReceivedHandlingUnitReceiptLine ::= ReceiptLineType

ReceiverParty ::= PartyType

RecipientCustomerParty ::= CustomerPartyType

RecipientParty ::= PartyType

ReferencedContract ::= ContractType

ReferencedGoodsItem ::= GoodsItemType

ReferencedPackage ::= PackageType

ReferencedTransportEquipment ::= TransportEquipmentType

ReferencedTransportHandlingUnit ::= TransportHandlingUnitType

RegistrationAddress ::= AddressType

Regulation ::= RegulationType

RelatedCatalogueReference ::= CatalogueReferenceType

RelatedItem ::= RelatedItemType

ReminderDocumentReference ::= DocumentReferenceType

ReminderLine ::= ReminderLineType

ReminderPeriod ::= PeriodType

RemittanceAdviceLine ::= RemittanceAdviceLineType

Renewal ::= RenewalType

ReplacementRelatedItem ::= RelatedItemType

ReportedShipment ::= ShipmentType

RequestForQuotationDocumentReference ::= DocumentReferenceType

RequestForQuotationLine ::= RequestForQuotationLineType

RequestForTenderLine ::= RequestForTenderLineType

RequestLineReference ::= LineReferenceType

RequestedCatalogueReference ::= CatalogueReferenceType

RequestedClassificationScheme ::= ClassificationSchemeType

RequestedDeliveryPeriod ::= PeriodType

RequestedDespatchPeriod ::= PeriodType

RequestedDocumentReference ::= DocumentReferenceType

RequestedLanguage ::= LanguageType

RequestedMonetaryTotal ::= MonetaryTotalType

RequestedValidityPeriod ::= PeriodType

RequiredBusinessClassificationScheme ::= ClassificationSchemeType

RequiredClassificationScheme ::= ClassificationSchemeType

RequiredCommodityClassification ::= CommodityClassificationType

RequiredFinancialGuarantee ::= FinancialGuaranteeType

RequiredItemLocationQuantity ::= ItemLocationQuantityType

RequiredRelatedItem ::= RelatedItemType

ResolutionDocumentReference ::= DocumentReferenceType

Response ::= ResponseType

ResultOfVerification ::= ResultOfVerificationType

RetailPlannedImpact ::= RetailPlannedImpactType

RetailerCustomerParty ::= CustomerPartyType

ReturnAddress ::= AddressType

RoadTransport ::= RoadTransportType

SalesItem ::= SalesItemType

SecondaryHazard ::= SecondaryHazardType

SelfBilledCreditNoteDocumentReference ::= DocumentReferenceType

SelfBilledInvoiceDocumentReference ::= DocumentReferenceType

SellerContact ::= ContactType

SellerProposedSubstituteLineItem ::= LineItemType

SellerSubstitutedLineItem ::= LineItemType

SellerSupplierParty ::= SupplierPartyType

SellersItemIdentification ::= ItemIdentificationType

SenderParty ::= PartyType

ServiceAllowanceCharge ::= AllowanceChargeType

ServiceEndTimePeriod ::= PeriodType

ServicePoint ::= ServicePointType

ServicePointLocation ::= LocationType

ServiceProviderParty ::= ServiceProviderPartyType

ServiceStartTimePeriod ::= PeriodType

SettlementPeriod ::= PeriodType

ShareholderParty ::= ShareholderPartyType

Shipment ::= ShipmentType

ShipmentDocumentReference ::= DocumentReferenceType

ShipmentStage ::= ShipmentStageType

SignatoryContact ::= ContactType

SignatoryParty ::= PartyType

Signature-1 ::= SignatureType-1

SourceCatalogueReference ::= CatalogueReferenceType

SourceIssuerParty ::= PartyType

SpecificTendererRequirement ::= TendererRequirementType

StandardItemIdentification ::= ItemIdentificationType

StatementDocumentReference ::= DocumentReferenceType

StatementLine ::= StatementLineType

StatementPeriod ::= PeriodType

Status ::= StatusType

StatusLocation ::= LocationType

StockAvailabilityReportLine ::= StockAvailabilityReportLineType

StorageLocation ::= LocationType

StorageTransportEvent ::= TransportEventType

Stowage ::= StowageType

SubCreditNoteLine ::= CreditNoteLineType

SubDebitNoteLine ::= DebitNoteLineType

SubInvoiceLine ::= InvoiceLineType

SubLineItem ::= LineItemType

SubRequestForTenderLine ::= RequestForTenderLineType

SubTenderLine ::= TenderLineType

SubcontractTerms ::= SubcontractTermsType

SubcontractorParty ::= PartyType

SubordinateAwardingCriteria ::= AwardingCriteriaType

SubordinateAwardingCriteriaResponse ::= AwardingCriteriaResponseType

SubscriberConsumption ::= SubscriberConsumptionType

SubscriberParty ::= PartyType

SubsequentProcessTenderRequirement ::= TenderRequirementType

SubsidiaryLocation ::= LocationType

SubstituteCarrierParty ::= PartyType

SuggestedEvidence ::= EvidenceType

SupplierConsumption ::= SupplierConsumptionType

SupplierParty ::= SupplierPartyType

SupplyChainActivityDataLine ::= ActivityDataLineType

SupplyItem ::= ItemType

SupportingDocumentReference ::= DocumentReferenceType

TakeoverTransportEvent ::= TransportEventType

TaxCategory ::= TaxCategoryType

TaxExchangeRate ::= ExchangeRateType

TaxExclusivePrice ::= PriceType

TaxInclusivePrice ::= PriceType

TaxRepresentativeParty ::= PartyType

TaxScheme ::= TaxSchemeType

TaxSubtotal ::= TaxSubtotalType

TaxTotal ::= TaxTotalType

TechnicalCapability ::= CapabilityType

TechnicalCommitteePerson ::= PersonType

TechnicalDocumentReference ::= DocumentReferenceType

TechnicalEvaluationCriteria ::= EvaluationCriteriaType

TelecommunicationsService ::= TelecommunicationsServiceType

TelecommunicationsSupply ::= TelecommunicationsSupplyType

TelecommunicationsSupplyLine ::= TelecommunicationsSupplyLineType

Temperature ::= TemperatureType

TemplateDocumentReference ::= DocumentReferenceType

TenderDocumentReference ::= DocumentReferenceType

TenderEvaluationParty ::= PartyType

TenderLine ::= TenderLineType

TenderPreparation ::= TenderPreparationType

TenderRecipientParty ::= PartyType

TenderRequirement ::= TenderRequirementType

TenderResult ::= TenderResultType

TenderSubmissionDeadlinePeriod ::= PeriodType

TenderValidityPeriod ::= PeriodType

TenderedProject ::= TenderedProjectType

TendererParty ::= PartyType

TendererPartyQualification ::= TendererPartyQualificationType

TendererQualificationRequest ::= TendererQualificationRequestType

TendererRequirement ::= TendererRequirementType

TenderingProcess ::= TenderingProcessType

TenderingTerms ::= TenderingTermsType

TerminalOperatorParty ::= PartyType

TimeDuty ::= DutyType

ToLocation ::= LocationType

TradeFinancing ::= TradeFinancingType

TradingTerms ::= TradingTermsType

TransactionConditions ::= TransactionConditionsType

TransitCountry ::= CountryType

TransitPeriod ::= PeriodType

TransportAdvisorParty ::= PartyType

TransportContract ::= ContractType

TransportEquipment ::= TransportEquipmentType

TransportEquipmentSeal ::= TransportEquipmentSealType

TransportEvent ::= TransportEventType

TransportExecutionTerms ::= TransportExecutionTermsType

TransportHandlingUnit ::= TransportHandlingUnitType

TransportLocation ::= TransportLocationType

TransportMeans ::= TransportMeansType

TransportSchedule ::= TransportScheduleType

TransportServiceDescriptionDocumentReference ::= DocumentReferenceType

TransportServiceProviderParty ::= PartyType

TransportServiceProviderResponseDeadlinePeriod ::= PeriodType

TransportStatus ::= TransportStatusType

TransportUserParty ::= PartyType

TransportUserReferenceParty ::= PartyType

TransportUserResponseDeadlinePeriod ::= PeriodType

TransportationSegment ::= TransportationSegmentType

TransportationService ::= TransportationServiceType

TransshipPortLocation ::= LocationType

UnloadingLocation ::= LocationType

UnloadingPortLocation ::= LocationType

UnstructuredPrice ::= UnstructuredPriceType

UpdatedDelivery ::= DeliveryType

UpdatedDespatch ::= DespatchType

UsabilityPeriod ::= PeriodType

UtilityConsumptionPoint ::= ConsumptionPointType

UtilityCustomerParty ::= PartyType

UtilityItem ::= UtilityItemType

UtilityMeter ::= MeterType

UtilitySupplierParty ::= PartyType

ValidityPeriod ::= PeriodType

WarehousingTransportEvent ::= TransportEventType

WarrantyParty ::= PartyType

WarrantyValidityPeriod ::= PeriodType

WebSiteAccess ::= WebSiteAccessType

WinningParty ::= PartyType

ActivityDataLineType ::= SEQUENCE {
    iD         ID-1,
    supplyChainActivityTypeCode SupplyChainActivityTypeCode,
    buyerCustomerParty BuyerCustomerParty OPTIONAL,
    sellerSupplierParty SellerSupplierParty OPTIONAL,
    activityPeriod ActivityPeriod OPTIONAL,
    activityOriginLocation ActivityOriginLocation,
    activityFinalLocation ActivityFinalLocation OPTIONAL,
    salesItem-list SEQUENCE (SIZE(1..MAX)) OF salesItem SalesItem
}

ActivityPropertyType ::= SEQUENCE {
    name  Name-1,
    value Value
}

AddressType ::= SEQUENCE {
    iD         ID-1 OPTIONAL,
    addressTypeCode AddressTypeCode OPTIONAL,
    addressFormatCode AddressFormatCode OPTIONAL,
    postbox    Postbox OPTIONAL,
    floor      Floor OPTIONAL,
    room       Room OPTIONAL,
    streetName StreetName OPTIONAL,
    additionalStreetName AdditionalStreetName OPTIONAL,
    blockName  BlockName OPTIONAL,
    buildingName BuildingName OPTIONAL,
    buildingNumber BuildingNumber OPTIONAL,
    inhouseMail InhouseMail OPTIONAL,
    department Department OPTIONAL,
    markAttention MarkAttention OPTIONAL,
    markCare   MarkCare OPTIONAL,
    plotIdentification PlotIdentification OPTIONAL,
    citySubdivisionName CitySubdivisionName OPTIONAL,
    cityName   CityName OPTIONAL,
    postalZone PostalZone OPTIONAL,
    countrySubentity CountrySubentity OPTIONAL,
    countrySubentityCode CountrySubentityCode OPTIONAL,
    region     Region OPTIONAL,
    district   District OPTIONAL,
    timezoneOffset TimezoneOffset OPTIONAL,
    addressLine-list SEQUENCE OF addressLine AddressLine,
    country    Country OPTIONAL,
    locationCoordinate-list SEQUENCE OF locationCoordinate LocationCoordinate
}

AddressLineType ::= SEQUENCE {
    line Line
}

AirTransportType ::= SEQUENCE {
    aircraftID AircraftID
}

AllowanceChargeType ::= SEQUENCE {
    iD         ID-1 OPTIONAL,
    chargeIndicator ChargeIndicator,
    allowanceChargeReasonCode AllowanceChargeReasonCode OPTIONAL,
    allowanceChargeReason AllowanceChargeReason OPTIONAL,
    multiplierFactorNumeric MultiplierFactorNumeric OPTIONAL,
    prepaidIndicator PrepaidIndicator OPTIONAL,
    sequenceNumeric SequenceNumeric OPTIONAL,
    amount     Amount,
    baseAmount BaseAmount OPTIONAL,
    accountingCostCode AccountingCostCode OPTIONAL,
    accountingCost AccountingCost OPTIONAL,
    perUnitAmount PerUnitAmount OPTIONAL,
    taxCategory-list SEQUENCE OF taxCategory TaxCategory,
    taxTotal   TaxTotal OPTIONAL,
    paymentMeans-list SEQUENCE OF paymentMeans PaymentMeans
}

AppealTermsType ::= SEQUENCE {
    description-list   SEQUENCE OF description Description,
    presentationPeriod PresentationPeriod OPTIONAL,
    appealInformationParty AppealInformationParty OPTIONAL,
    appealReceiverParty AppealReceiverParty OPTIONAL,
    mediationParty     MediationParty OPTIONAL
}

AttachmentType ::= SEQUENCE {
    embeddedDocumentBinaryObject EmbeddedDocumentBinaryObject OPTIONAL,
    externalReference      ExternalReference OPTIONAL
}

AuctionTermsType ::= SEQUENCE {
    auctionConstraintIndicator AuctionConstraintIndicator OPTIONAL,
    justificationDescription-list SEQUENCE OF justificationDescription 
	JustificationDescription,
    description-list   SEQUENCE OF description Description,
    processDescription-list SEQUENCE OF processDescription ProcessDescription,
    conditionsDescription-list SEQUENCE OF conditionsDescription 
	ConditionsDescription,
    electronicDeviceDescription-list SEQUENCE OF electronicDeviceDescription 
	ElectronicDeviceDescription,
    auctionURI         AuctionURI OPTIONAL
}

AwardingCriteriaType ::= SEQUENCE {
    iD         ID-1 OPTIONAL,
    awardingCriteriaTypeCode AwardingCriteriaTypeCode OPTIONAL,
    description-list SEQUENCE OF description Description,
    weightNumeric WeightNumeric OPTIONAL,
    weight-list SEQUENCE OF weight Weight,
    calculationExpression-list SEQUENCE OF calculationExpression 
	CalculationExpression,
    calculationExpressionCode CalculationExpressionCode OPTIONAL,
    minimumQuantity MinimumQuantity OPTIONAL,
    maximumQuantity MaximumQuantity OPTIONAL,
    minimumAmount MinimumAmount OPTIONAL,
    maximumAmount MaximumAmount OPTIONAL,
    minimumImprovementBid-list SEQUENCE OF minimumImprovementBid 
	MinimumImprovementBid,
    subordinateAwardingCriteria-list SEQUENCE OF subordinateAwardingCriteria 
	SubordinateAwardingCriteria
}

AwardingCriteriaResponseType ::= SEQUENCE {
    iD         ID-1 OPTIONAL,
    awardingCriteriaID AwardingCriteriaID OPTIONAL,
    awardingCriteriaDescription-list SEQUENCE OF awardingCriteriaDescription 
	AwardingCriteriaDescription,
    description-list SEQUENCE OF description Description,
    quantity   Quantity OPTIONAL,
    amount     Amount OPTIONAL,
    subordinateAwardingCriteriaResponse-list SEQUENCE OF 
	subordinateAwardingCriteriaResponse 
	SubordinateAwardingCriteriaResponse
}

AwardingTermsType ::= SEQUENCE {
    weightingAlgorithmCode    WeightingAlgorithmCode OPTIONAL,
    description-list          SEQUENCE OF description Description,
    technicalCommitteeDescription-list SEQUENCE OF 
	technicalCommitteeDescription TechnicalCommitteeDescription,
    lowTendersDescription-list SEQUENCE OF lowTendersDescription 
	LowTendersDescription,
    awardingCriteria-list     SEQUENCE OF awardingCriteria AwardingCriteria,
    technicalCommitteePerson-list SEQUENCE OF technicalCommitteePerson 
	TechnicalCommitteePerson
}

BillingReferenceType ::= SEQUENCE {
    invoiceDocumentReference       InvoiceDocumentReference OPTIONAL,
    selfBilledInvoiceDocumentReference SelfBilledInvoiceDocumentReference
	OPTIONAL,
    creditNoteDocumentReference    CreditNoteDocumentReference OPTIONAL,
    selfBilledCreditNoteDocumentReference 
	SelfBilledCreditNoteDocumentReference OPTIONAL,
    debitNoteDocumentReference     DebitNoteDocumentReference OPTIONAL,
    reminderDocumentReference      ReminderDocumentReference OPTIONAL,
    additionalDocumentReference    AdditionalDocumentReference OPTIONAL,
    billingReferenceLine-list      SEQUENCE OF billingReferenceLine 
	BillingReferenceLine
}

BillingReferenceLineType ::= SEQUENCE {
    iD                   ID-1,
    amount               Amount OPTIONAL,
    allowanceCharge-list SEQUENCE OF allowanceCharge AllowanceCharge
}

BranchType ::= SEQUENCE {
    iD                   ID-1 OPTIONAL,
    name                 Name-1 OPTIONAL,
    financialInstitution FinancialInstitution OPTIONAL,
    address              Address OPTIONAL
}

BudgetAccountType ::= SEQUENCE {
    iD         ID-1 OPTIONAL,
    budgetYearNumeric BudgetYearNumeric OPTIONAL,
    requiredClassificationScheme RequiredClassificationScheme OPTIONAL
}

BudgetAccountLineType ::= SEQUENCE {
    iD                 ID-1 OPTIONAL,
    totalAmount        TotalAmount OPTIONAL,
    budgetAccount-list SEQUENCE OF budgetAccount BudgetAccount
}

BudgetAmountType ::= SEQUENCE {
    estimatedOverallContractAmount EstimatedOverallContractAmount OPTIONAL,
    totalAmount           TotalAmount OPTIONAL,
    taxExclusiveAmount    TaxExclusiveAmount OPTIONAL,
    minimumAmount         MinimumAmount OPTIONAL,
    monetaryScope-list    SEQUENCE OF monetaryScope MonetaryScope,
    averageSubsequentContractAmount AverageSubsequentContractAmount OPTIONAL,
    applicableTaxCategory-list SEQUENCE OF applicableTaxCategory 
	ApplicableTaxCategory
}

CapabilityType ::= SEQUENCE {
    capabilityTypeCode CapabilityTypeCode OPTIONAL,
    description-list  SEQUENCE OF description Description,
    valueAmount       ValueAmount OPTIONAL,
    valueQuantity     ValueQuantity OPTIONAL,
    evidenceSuppliedID-list SEQUENCE OF evidenceSuppliedID EvidenceSuppliedID,
    validityPeriod    ValidityPeriod OPTIONAL
}

CardAccountType ::= SEQUENCE {
    primaryAccountNumberID PrimaryAccountNumberID,
    networkID     NetworkID,
    cardTypeCode  CardTypeCode OPTIONAL,
    validityStartDate ValidityStartDate OPTIONAL,
    expiryDate    ExpiryDate OPTIONAL,
    issuerID      IssuerID OPTIONAL,
    issueNumberID IssueNumberID OPTIONAL,
    cV2ID         CV2ID OPTIONAL,
    cardChipCode  CardChipCode OPTIONAL,
    chipApplicationID ChipApplicationID OPTIONAL,
    holderName    HolderName OPTIONAL
}

CatalogueItemSpecificationUpdateLineType ::= SEQUENCE {
    iD         ID-1,
    contractorCustomerParty ContractorCustomerParty OPTIONAL,
    sellerSupplierParty SellerSupplierParty OPTIONAL,
    item       Item
}

CatalogueLineType ::= SEQUENCE {
    iD         ID-1,
    actionCode ActionCode OPTIONAL,
    lifeCycleStatusCode LifeCycleStatusCode OPTIONAL,
    contractSubdivision ContractSubdivision OPTIONAL,
    note-list  SEQUENCE OF note Note,
    orderableIndicator OrderableIndicator OPTIONAL,
    orderableUnit OrderableUnit OPTIONAL,
    contentUnitQuantity ContentUnitQuantity OPTIONAL,
    orderQuantityIncrementNumeric OrderQuantityIncrementNumeric OPTIONAL,
    minimumOrderQuantity MinimumOrderQuantity OPTIONAL,
    maximumOrderQuantity MaximumOrderQuantity OPTIONAL,
    warrantyInformation-list SEQUENCE OF warrantyInformation 
	WarrantyInformation,
    packLevelCode PackLevelCode OPTIONAL,
    contractorCustomerParty ContractorCustomerParty OPTIONAL,
    sellerSupplierParty SellerSupplierParty OPTIONAL,
    warrantyParty WarrantyParty OPTIONAL,
    warrantyValidityPeriod WarrantyValidityPeriod OPTIONAL,
    lineValidityPeriod LineValidityPeriod OPTIONAL,
    itemComparison-list SEQUENCE OF itemComparison ItemComparison,
    componentRelatedItem-list SEQUENCE OF componentRelatedItem 
	ComponentRelatedItem,
    accessoryRelatedItem-list SEQUENCE OF accessoryRelatedItem 
	AccessoryRelatedItem,
    requiredRelatedItem-list SEQUENCE OF requiredRelatedItem 
	RequiredRelatedItem,
    replacementRelatedItem-list SEQUENCE OF replacementRelatedItem 
	ReplacementRelatedItem,
    complementaryRelatedItem-list SEQUENCE OF complementaryRelatedItem 
	ComplementaryRelatedItem,
    requiredItemLocationQuantity-list SEQUENCE OF requiredItemLocationQuantity
	RequiredItemLocationQuantity,
    documentReference-list SEQUENCE OF documentReference DocumentReference,
    item       Item,
    keywordItemProperty-list SEQUENCE OF keywordItemProperty 
	KeywordItemProperty
}

CataloguePricingUpdateLineType ::= SEQUENCE {
    iD         ID-1,
    contractorCustomerParty ContractorCustomerParty OPTIONAL,
    sellerSupplierParty SellerSupplierParty OPTIONAL,
    requiredItemLocationQuantity-list SEQUENCE OF requiredItemLocationQuantity
	RequiredItemLocationQuantity
}

CatalogueReferenceType ::= SEQUENCE {
    iD                ID-1,
    uUID              UUID OPTIONAL,
    issueDate         IssueDate OPTIONAL,
    issueTime         IssueTime OPTIONAL,
    revisionDate      RevisionDate OPTIONAL,
    revisionTime      RevisionTime OPTIONAL,
    note-list         SEQUENCE OF note Note,
    description-list  SEQUENCE OF description Description,
    versionID         VersionID OPTIONAL,
    previousVersionID PreviousVersionID OPTIONAL
}

CatalogueRequestLineType ::= SEQUENCE {
    iD         ID-1,
    contractSubdivision ContractSubdivision OPTIONAL,
    note-list  SEQUENCE OF note Note,
    lineValidityPeriod LineValidityPeriod OPTIONAL,
    requiredItemLocationQuantity-list SEQUENCE OF requiredItemLocationQuantity
	RequiredItemLocationQuantity,
    item       Item
}

CertificateType ::= SEQUENCE {
    iD           ID-1,
    certificateTypeCode CertificateTypeCode,
    certificateType CertificateType-1,
    remarks      Remarks OPTIONAL,
    issuerParty  IssuerParty,
    documentReference-list SEQUENCE OF documentReference DocumentReference,
    signature-list SEQUENCE OF signature Signature-1
}

CertificateOfOriginApplicationType ::= SEQUENCE {
    referenceID     ReferenceID,
    certificateType CertificateType-1,
    applicationStatusCode ApplicationStatusCode OPTIONAL,
    originalJobID   OriginalJobID,
    previousJobID   PreviousJobID OPTIONAL,
    remarks         Remarks OPTIONAL,
    shipment        Shipment,
    endorserParty-list SEQUENCE (SIZE(1..MAX)) OF endorserParty EndorserParty,
    preparationParty PreparationParty,
    issuerParty     IssuerParty,
    exporterParty   ExporterParty OPTIONAL,
    importerParty   ImporterParty OPTIONAL,
    issuingCountry  IssuingCountry,
    documentDistribution-list SEQUENCE OF documentDistribution 
	DocumentDistribution,
    supportingDocumentReference-list SEQUENCE OF supportingDocumentReference 
	SupportingDocumentReference,
    signature-list  SEQUENCE OF signature Signature-1
}

ClassificationCategoryType ::= SEQUENCE {
    name         Name-1 OPTIONAL,
    codeValue    CodeValue OPTIONAL,
    description-list SEQUENCE OF description Description,
    categorizesClassificationCategory-list SEQUENCE OF 
	categorizesClassificationCategory CategorizesClassificationCategory
}

ClassificationSchemeType ::= SEQUENCE {
    iD         ID-1,
    uUID       UUID OPTIONAL,
    lastRevisionDate LastRevisionDate OPTIONAL,
    lastRevisionTime LastRevisionTime OPTIONAL,
    note-list  SEQUENCE OF note Note,
    name       Name-1 OPTIONAL,
    description-list SEQUENCE OF description Description,
    agencyID   AgencyID OPTIONAL,
    agencyName AgencyName OPTIONAL,
    versionID  VersionID OPTIONAL,
    uRI        URI OPTIONAL,
    schemeURI  SchemeURI OPTIONAL,
    languageID LanguageID OPTIONAL,
    classificationCategory-list SEQUENCE (SIZE(1..MAX)) OF 
	classificationCategory ClassificationCategory
}

CommodityClassificationType ::= SEQUENCE {
    natureCode       NatureCode OPTIONAL,
    cargoTypeCode    CargoTypeCode OPTIONAL,
    commodityCode    CommodityCode OPTIONAL,
    itemClassificationCode ItemClassificationCode OPTIONAL
}

CommunicationType ::= SEQUENCE {
    channelCode ChannelCode OPTIONAL,
    channel     Channel OPTIONAL,
    value       Value OPTIONAL
}

CompletedTaskType ::= SEQUENCE {
    annualAverageAmount AnnualAverageAmount OPTIONAL,
    totalTaskAmount TotalTaskAmount OPTIONAL,
    partyCapacityAmount PartyCapacityAmount OPTIONAL,
    description-list SEQUENCE OF description Description,
    evidenceSuppliedID EvidenceSuppliedID OPTIONAL,
    period         Period OPTIONAL,
    recipientCustomerParty RecipientCustomerParty OPTIONAL
}

ConsignmentType ::= SEQUENCE {
    iD         ID-1,
    carrierAssignedID CarrierAssignedID OPTIONAL,
    consigneeAssignedID ConsigneeAssignedID OPTIONAL,
    consignorAssignedID ConsignorAssignedID OPTIONAL,
    freightForwarderAssignedID FreightForwarderAssignedID OPTIONAL,
    brokerAssignedID BrokerAssignedID OPTIONAL,
    contractedCarrierAssignedID ContractedCarrierAssignedID OPTIONAL,
    performingCarrierAssignedID PerformingCarrierAssignedID OPTIONAL,
    summaryDescription-list SEQUENCE OF summaryDescription SummaryDescription,
    totalInvoiceAmount TotalInvoiceAmount OPTIONAL,
    declaredCustomsValueAmount DeclaredCustomsValueAmount OPTIONAL,
    tariffDescription-list SEQUENCE OF tariffDescription TariffDescription,
    tariffCode TariffCode OPTIONAL,
    insurancePremiumAmount InsurancePremiumAmount OPTIONAL,
    grossWeightMeasure GrossWeightMeasure OPTIONAL,
    netWeightMeasure NetWeightMeasure OPTIONAL,
    netNetWeightMeasure NetNetWeightMeasure OPTIONAL,
    chargeableWeightMeasure ChargeableWeightMeasure OPTIONAL,
    grossVolumeMeasure GrossVolumeMeasure OPTIONAL,
    netVolumeMeasure NetVolumeMeasure OPTIONAL,
    loadingLengthMeasure LoadingLengthMeasure OPTIONAL,
    remarks-list SEQUENCE OF remarks Remarks,
    hazardousRiskIndicator HazardousRiskIndicator OPTIONAL,
    animalFoodIndicator AnimalFoodIndicator OPTIONAL,
    humanFoodIndicator HumanFoodIndicator OPTIONAL,
    livestockIndicator LivestockIndicator OPTIONAL,
    bulkCargoIndicator BulkCargoIndicator OPTIONAL,
    containerizedIndicator ContainerizedIndicator OPTIONAL,
    generalCargoIndicator GeneralCargoIndicator OPTIONAL,
    specialSecurityIndicator SpecialSecurityIndicator OPTIONAL,
    thirdPartyPayerIndicator ThirdPartyPayerIndicator OPTIONAL,
    carrierServiceInstructions CarrierServiceInstructions OPTIONAL,
    customsClearanceServiceInstructions CustomsClearanceServiceInstructions
	OPTIONAL,
    forwarderServiceInstructions ForwarderServiceInstructions OPTIONAL,
    specialServiceInstructions SpecialServiceInstructions OPTIONAL,
    sequenceID SequenceID OPTIONAL,
    shippingPriorityLevelCode ShippingPriorityLevelCode OPTIONAL,
    handlingCode HandlingCode OPTIONAL,
    handlingInstructions HandlingInstructions OPTIONAL,
    information Information OPTIONAL,
    totalGoodsItemQuantity TotalGoodsItemQuantity OPTIONAL,
    totalTransportHandlingUnitQuantity TotalTransportHandlingUnitQuantity
	OPTIONAL,
    insuranceValueAmount InsuranceValueAmount OPTIONAL,
    declaredForCarriageValueAmount DeclaredForCarriageValueAmount OPTIONAL,
    declaredStatisticsValueAmount DeclaredStatisticsValueAmount OPTIONAL,
    freeOnBoardValueAmount FreeOnBoardValueAmount OPTIONAL,
    specialInstructions-list SEQUENCE OF specialInstructions 
	SpecialInstructions,
    splitConsignmentIndicator SplitConsignmentIndicator OPTIONAL,
    deliveryInstructions-list SEQUENCE OF deliveryInstructions 
	DeliveryInstructions,
    consignmentQuantity ConsignmentQuantity OPTIONAL,
    consolidatableIndicator ConsolidatableIndicator OPTIONAL,
    haulageInstructions-list SEQUENCE OF haulageInstructions 
	HaulageInstructions,
    loadingSequenceID LoadingSequenceID OPTIONAL,
    consigneeParty ConsigneeParty OPTIONAL,
    exporterParty ExporterParty OPTIONAL,
    consignorParty ConsignorParty OPTIONAL,
    importerParty ImporterParty OPTIONAL,
    carrierParty CarrierParty OPTIONAL,
    freightForwarderParty FreightForwarderParty OPTIONAL,
    notifyParty NotifyParty OPTIONAL,
    originalDespatchParty OriginalDespatchParty OPTIONAL,
    finalDeliveryParty FinalDeliveryParty OPTIONAL,
    performingCarrierParty PerformingCarrierParty OPTIONAL,
    substituteCarrierParty SubstituteCarrierParty OPTIONAL,
    logisticsOperatorParty LogisticsOperatorParty OPTIONAL,
    transportAdvisorParty TransportAdvisorParty OPTIONAL,
    hazardousItemNotificationParty HazardousItemNotificationParty OPTIONAL,
    insuranceParty InsuranceParty OPTIONAL,
    mortgageHolderParty MortgageHolderParty OPTIONAL,
    billOfLadingHolderParty BillOfLadingHolderParty OPTIONAL,
    originalDepartureCountry OriginalDepartureCountry OPTIONAL,
    finalDestinationCountry FinalDestinationCountry OPTIONAL,
    transitCountry-list SEQUENCE OF transitCountry TransitCountry,
    transportContract TransportContract OPTIONAL,
    originalDespatchTransportationService 
	OriginalDespatchTransportationService OPTIONAL,
    finalDeliveryTransportationService FinalDeliveryTransportationService
	OPTIONAL,
    deliveryTerms DeliveryTerms OPTIONAL,
    paymentTerms PaymentTerms OPTIONAL,
    collectPaymentTerms CollectPaymentTerms OPTIONAL,
    disbursementPaymentTerms DisbursementPaymentTerms OPTIONAL,
    prepaidPaymentTerms PrepaidPaymentTerms OPTIONAL,
    freightAllowanceCharge-list SEQUENCE OF freightAllowanceCharge 
	FreightAllowanceCharge,
    extraAllowanceCharge-list SEQUENCE OF extraAllowanceCharge 
	ExtraAllowanceCharge,
    mainCarriageShipmentStage MainCarriageShipmentStage OPTIONAL,
    preCarriageShipmentStage-list SEQUENCE OF preCarriageShipmentStage 
	PreCarriageShipmentStage,
    onCarriageShipmentStage-list SEQUENCE OF onCarriageShipmentStage 
	OnCarriageShipmentStage,
    transportHandlingUnit-list SEQUENCE OF transportHandlingUnit 
	TransportHandlingUnit,
    firstArrivalPortLocation FirstArrivalPortLocation OPTIONAL,
    lastExitPortLocation LastExitPortLocation OPTIONAL,
    consolidatedShipment-list SEQUENCE OF consolidatedShipment 
	ConsolidatedShipment
}

ConsumptionType ::= SEQUENCE {
    utilityStatementTypeCode UtilityStatementTypeCode OPTIONAL,
    mainPeriod        MainPeriod OPTIONAL,
    allowanceCharge-list SEQUENCE OF allowanceCharge AllowanceCharge,
    taxTotal-list     SEQUENCE OF taxTotal TaxTotal,
    energyWaterSupply EnergyWaterSupply OPTIONAL,
    telecommunicationsSupply TelecommunicationsSupply OPTIONAL,
    legalMonetaryTotal LegalMonetaryTotal
}

ConsumptionAverageType ::= SEQUENCE {
    averageAmount AverageAmount OPTIONAL,
    description   Description OPTIONAL
}

ConsumptionHistoryType ::= SEQUENCE {
    meterNumber          MeterNumber OPTIONAL,
    quantity             Quantity,
    amount               Amount OPTIONAL,
    consumptionLevelCode ConsumptionLevelCode OPTIONAL,
    consumptionLevel     ConsumptionLevel OPTIONAL,
    description-list     SEQUENCE OF description Description,
    period               Period
}

ConsumptionLineType ::= SEQUENCE {
    iD         ID-1,
    parentDocumentLineReferenceID ParentDocumentLineReferenceID OPTIONAL,
    invoicedQuantity InvoicedQuantity,
    lineExtensionAmount LineExtensionAmount,
    period     Period OPTIONAL,
    delivery-list SEQUENCE OF delivery Delivery,
    allowanceCharge-list SEQUENCE OF allowanceCharge AllowanceCharge,
    taxTotal-list SEQUENCE OF taxTotal TaxTotal,
    utilityItem UtilityItem,
    price      Price OPTIONAL,
    unstructuredPrice UnstructuredPrice OPTIONAL
}

ConsumptionPointType ::= SEQUENCE {
    iD         ID-1,
    description Description OPTIONAL,
    subscriberID SubscriberID OPTIONAL,
    subscriberTypeIdentifier SubscriberTypeIdentifier OPTIONAL,
    subscriberTypeCode SubscriberTypeCode OPTIONAL,
    totalDeliveredQuantity TotalDeliveredQuantity OPTIONAL,
    address    Address OPTIONAL,
    webSiteAccess WebSiteAccess OPTIONAL,
    utilityMeter-list SEQUENCE OF utilityMeter UtilityMeter
}

ConsumptionReportType ::= SEQUENCE {
    iD         ID-1,
    consumptionType ConsumptionType-1 OPTIONAL,
    consumptionTypeCode ConsumptionTypeCode OPTIONAL,
    description-list SEQUENCE OF description Description,
    totalConsumedQuantity TotalConsumedQuantity OPTIONAL,
    basicConsumedQuantity BasicConsumedQuantity OPTIONAL,
    residentOccupantsNumeric ResidentOccupantsNumeric OPTIONAL,
    consumersEnergyLevelCode ConsumersEnergyLevelCode OPTIONAL,
    consumersEnergyLevel ConsumersEnergyLevel OPTIONAL,
    residenceType ResidenceType OPTIONAL,
    residenceTypeCode ResidenceTypeCode OPTIONAL,
    heatingType HeatingType OPTIONAL,
    heatingTypeCode HeatingTypeCode OPTIONAL,
    period     Period OPTIONAL,
    guidanceDocumentReference GuidanceDocumentReference OPTIONAL,
    documentReference DocumentReference OPTIONAL,
    consumptionReportReference-list SEQUENCE OF consumptionReportReference 
	ConsumptionReportReference,
    consumptionHistory-list SEQUENCE OF consumptionHistory ConsumptionHistory
}

ConsumptionReportReferenceType ::= SEQUENCE {
    consumptionReportID ConsumptionReportID,
    consumptionType ConsumptionType-1 OPTIONAL,
    consumptionTypeCode ConsumptionTypeCode OPTIONAL,
    totalConsumedQuantity TotalConsumedQuantity,
    period        Period
}

ContactType ::= SEQUENCE {
    iD         ID-1 OPTIONAL,
    name       Name-1 OPTIONAL,
    telephone  Telephone OPTIONAL,
    telefax    Telefax OPTIONAL,
    electronicMail ElectronicMail OPTIONAL,
    note-list  SEQUENCE OF note Note,
    otherCommunication-list SEQUENCE OF otherCommunication OtherCommunication
}

ContractType ::= SEQUENCE {
    iD         ID-1 OPTIONAL,
    issueDate  IssueDate OPTIONAL,
    issueTime  IssueTime OPTIONAL,
    nominationDate NominationDate OPTIONAL,
    nominationTime NominationTime OPTIONAL,
    contractTypeCode ContractTypeCode OPTIONAL,
    contractType ContractType-1 OPTIONAL,
    note-list  SEQUENCE OF note Note,
    versionID  VersionID OPTIONAL,
    description-list SEQUENCE OF description Description,
    validityPeriod ValidityPeriod OPTIONAL,
    contractDocumentReference-list SEQUENCE OF contractDocumentReference 
	ContractDocumentReference,
    nominationPeriod NominationPeriod OPTIONAL,
    contractualDelivery ContractualDelivery OPTIONAL
}

ContractExecutionRequirementType ::= SEQUENCE {
    name-list        SEQUENCE OF name Name-1,
    executionRequirementCode ExecutionRequirementCode OPTIONAL,
    description-list SEQUENCE OF description Description
}

ContractExtensionType ::= SEQUENCE {
    optionsDescription-list SEQUENCE OF optionsDescription OptionsDescription,
    minimumNumberNumeric MinimumNumberNumeric OPTIONAL,
    maximumNumberNumeric MaximumNumberNumeric OPTIONAL,
    optionValidityPeriod OptionValidityPeriod OPTIONAL,
    renewal-list      SEQUENCE OF renewal Renewal
}

ContractingPartyType ::= SEQUENCE {
    contractingPartyTypeCode ContractingPartyTypeCode OPTIONAL,
    activityCode-list SEQUENCE OF activityCode ActivityCode,
    buyerProfileURI BuyerProfileURI OPTIONAL,
    party          Party
}

CorporateRegistrationSchemeType ::= SEQUENCE {
    iD         ID-1 OPTIONAL,
    name       Name-1 OPTIONAL,
    corporateRegistrationTypeCode CorporateRegistrationTypeCode OPTIONAL,
    jurisdictionRegionAddress-list SEQUENCE OF jurisdictionRegionAddress 
	JurisdictionRegionAddress
}

CorrectionType ::= SEQUENCE {
    correctionType      CorrectionType-1 OPTIONAL,
    correctionTypeCode  CorrectionTypeCode OPTIONAL,
    meterNumber         MeterNumber OPTIONAL,
    gasPressureQuantity GasPressureQuantity OPTIONAL,
    actualTemperatureReductionQuantity ActualTemperatureReductionQuantity
	OPTIONAL,
    normalTemperatureReductionQuantity NormalTemperatureReductionQuantity
	OPTIONAL,
    differenceTemperatureReductionQuantity 
	DifferenceTemperatureReductionQuantity OPTIONAL,
    description         Description OPTIONAL,
    correctionUnitAmount CorrectionUnitAmount OPTIONAL,
    consumptionEnergyQuantity ConsumptionEnergyQuantity OPTIONAL,
    consumptionWaterQuantity ConsumptionWaterQuantity OPTIONAL,
    correctionAmount    CorrectionAmount OPTIONAL
}

CountryType ::= SEQUENCE {
    identificationCode IdentificationCode OPTIONAL,
    name               Name-1 OPTIONAL
}

CreditAccountType ::= SEQUENCE {
    accountID AccountID
}

CreditNoteLineType ::= SEQUENCE {
    iD         ID-1,
    uUID       UUID OPTIONAL,
    note-list  SEQUENCE OF note Note,
    creditedQuantity CreditedQuantity OPTIONAL,
    lineExtensionAmount LineExtensionAmount OPTIONAL,
    taxPointDate TaxPointDate OPTIONAL,
    accountingCostCode AccountingCostCode OPTIONAL,
    accountingCost AccountingCost OPTIONAL,
    paymentPurposeCode PaymentPurposeCode OPTIONAL,
    freeOfChargeIndicator FreeOfChargeIndicator OPTIONAL,
    invoicePeriod-list SEQUENCE OF invoicePeriod InvoicePeriod,
    orderLineReference-list SEQUENCE OF orderLineReference OrderLineReference,
    discrepancyResponse-list SEQUENCE OF discrepancyResponse 
	DiscrepancyResponse,
    despatchLineReference-list SEQUENCE OF despatchLineReference 
	DespatchLineReference,
    receiptLineReference-list SEQUENCE OF receiptLineReference 
	ReceiptLineReference,
    billingReference-list SEQUENCE OF billingReference BillingReference,
    documentReference-list SEQUENCE OF documentReference DocumentReference,
    pricingReference PricingReference OPTIONAL,
    originatorParty OriginatorParty OPTIONAL,
    delivery-list SEQUENCE OF delivery Delivery,
    paymentTerms-list SEQUENCE OF paymentTerms PaymentTerms,
    taxTotal-list SEQUENCE OF taxTotal TaxTotal,
    allowanceCharge-list SEQUENCE OF allowanceCharge AllowanceCharge,
    item       Item OPTIONAL,
    price      Price OPTIONAL,
    deliveryTerms-list SEQUENCE OF deliveryTerms DeliveryTerms,
    subCreditNoteLine-list SEQUENCE OF subCreditNoteLine SubCreditNoteLine
}

CustomerPartyType ::= SEQUENCE {
    customerAssignedAccountID CustomerAssignedAccountID OPTIONAL,
    supplierAssignedAccountID SupplierAssignedAccountID OPTIONAL,
    additionalAccountID-list SEQUENCE OF additionalAccountID 
	AdditionalAccountID,
    party           Party OPTIONAL,
    deliveryContact DeliveryContact OPTIONAL,
    accountingContact AccountingContact OPTIONAL,
    buyerContact    BuyerContact OPTIONAL
}

DebitNoteLineType ::= SEQUENCE {
    iD         ID-1,
    uUID       UUID OPTIONAL,
    note-list  SEQUENCE OF note Note,
    debitedQuantity DebitedQuantity OPTIONAL,
    lineExtensionAmount LineExtensionAmount,
    taxPointDate TaxPointDate OPTIONAL,
    accountingCostCode AccountingCostCode OPTIONAL,
    accountingCost AccountingCost OPTIONAL,
    paymentPurposeCode PaymentPurposeCode OPTIONAL,
    discrepancyResponse-list SEQUENCE OF discrepancyResponse 
	DiscrepancyResponse,
    despatchLineReference-list SEQUENCE OF despatchLineReference 
	DespatchLineReference,
    receiptLineReference-list SEQUENCE OF receiptLineReference 
	ReceiptLineReference,
    billingReference-list SEQUENCE OF billingReference BillingReference,
    documentReference-list SEQUENCE OF documentReference DocumentReference,
    pricingReference PricingReference OPTIONAL,
    delivery-list SEQUENCE OF delivery Delivery,
    taxTotal-list SEQUENCE OF taxTotal TaxTotal,
    allowanceCharge-list SEQUENCE OF allowanceCharge AllowanceCharge,
    item       Item OPTIONAL,
    price      Price OPTIONAL,
    subDebitNoteLine-list SEQUENCE OF subDebitNoteLine SubDebitNoteLine
}

DeclarationType ::= SEQUENCE {
    name-list        SEQUENCE OF name Name-1,
    declarationTypeCode DeclarationTypeCode OPTIONAL,
    description-list SEQUENCE OF description Description,
    evidenceSuppliedID-list SEQUENCE OF evidenceSuppliedID EvidenceSuppliedID
}

DeliveryType ::= SEQUENCE {
    iD         ID-1 OPTIONAL,
    quantity   Quantity OPTIONAL,
    minimumQuantity MinimumQuantity OPTIONAL,
    maximumQuantity MaximumQuantity OPTIONAL,
    actualDeliveryDate ActualDeliveryDate OPTIONAL,
    actualDeliveryTime ActualDeliveryTime OPTIONAL,
    latestDeliveryDate LatestDeliveryDate OPTIONAL,
    latestDeliveryTime LatestDeliveryTime OPTIONAL,
    releaseID  ReleaseID OPTIONAL,
    trackingID TrackingID OPTIONAL,
    deliveryAddress DeliveryAddress OPTIONAL,
    deliveryLocation DeliveryLocation OPTIONAL,
    alternativeDeliveryLocation AlternativeDeliveryLocation OPTIONAL,
    requestedDeliveryPeriod RequestedDeliveryPeriod OPTIONAL,
    promisedDeliveryPeriod PromisedDeliveryPeriod OPTIONAL,
    estimatedDeliveryPeriod EstimatedDeliveryPeriod OPTIONAL,
    carrierParty CarrierParty OPTIONAL,
    deliveryParty DeliveryParty OPTIONAL,
    notifyParty-list SEQUENCE OF notifyParty NotifyParty,
    despatch   Despatch OPTIONAL,
    deliveryTerms-list SEQUENCE OF deliveryTerms DeliveryTerms,
    minimumDeliveryUnit MinimumDeliveryUnit OPTIONAL,
    maximumDeliveryUnit MaximumDeliveryUnit OPTIONAL,
    shipment   Shipment OPTIONAL
}

DeliveryTermsType ::= SEQUENCE {
    iD         ID-1 OPTIONAL,
    specialTerms SpecialTerms OPTIONAL,
    lossRiskResponsibilityCode LossRiskResponsibilityCode OPTIONAL,
    lossRisk   LossRisk OPTIONAL,
    amount     Amount OPTIONAL,
    deliveryLocation DeliveryLocation OPTIONAL,
    allowanceCharge AllowanceCharge OPTIONAL
}

DeliveryUnitType ::= SEQUENCE {
    batchQuantity     BatchQuantity,
    consumerUnitQuantity ConsumerUnitQuantity OPTIONAL,
    hazardousRiskIndicator HazardousRiskIndicator OPTIONAL
}

DependentPriceReferenceType ::= SEQUENCE {
    percent        Percent OPTIONAL,
    locationAddress LocationAddress OPTIONAL,
    dependentLineReference DependentLineReference OPTIONAL
}

DespatchType ::= SEQUENCE {
    iD         ID-1 OPTIONAL,
    requestedDespatchDate RequestedDespatchDate OPTIONAL,
    requestedDespatchTime RequestedDespatchTime OPTIONAL,
    estimatedDespatchDate EstimatedDespatchDate OPTIONAL,
    estimatedDespatchTime EstimatedDespatchTime OPTIONAL,
    actualDespatchDate ActualDespatchDate OPTIONAL,
    actualDespatchTime ActualDespatchTime OPTIONAL,
    guaranteedDespatchDate GuaranteedDespatchDate OPTIONAL,
    guaranteedDespatchTime GuaranteedDespatchTime OPTIONAL,
    releaseID  ReleaseID OPTIONAL,
    instructions Instructions OPTIONAL,
    despatchAddress DespatchAddress OPTIONAL,
    despatchLocation DespatchLocation OPTIONAL,
    despatchParty DespatchParty OPTIONAL,
    carrierParty CarrierParty OPTIONAL,
    notifyParty-list SEQUENCE OF notifyParty NotifyParty,
    contact    Contact OPTIONAL,
    estimatedDespatchPeriod EstimatedDespatchPeriod OPTIONAL,
    requestedDespatchPeriod RequestedDespatchPeriod OPTIONAL
}

DespatchLineType ::= SEQUENCE {
    iD         ID-1,
    uUID       UUID OPTIONAL,
    note-list  SEQUENCE OF note Note,
    lineStatusCode LineStatusCode OPTIONAL,
    deliveredQuantity DeliveredQuantity OPTIONAL,
    backorderQuantity BackorderQuantity OPTIONAL,
    backorderReason BackorderReason OPTIONAL,
    outstandingQuantity OutstandingQuantity OPTIONAL,
    outstandingReason OutstandingReason OPTIONAL,
    oversupplyQuantity OversupplyQuantity OPTIONAL,
    orderLineReference-list SEQUENCE (SIZE(1..MAX)) OF orderLineReference 
	OrderLineReference,
    documentReference-list SEQUENCE OF documentReference DocumentReference,
    item       Item,
    shipment-list SEQUENCE OF shipment Shipment
}

DimensionType ::= SEQUENCE {
    attributeID      AttributeID,
    measure          Measure OPTIONAL,
    description-list SEQUENCE OF description Description,
    minimumMeasure   MinimumMeasure OPTIONAL,
    maximumMeasure   MaximumMeasure OPTIONAL
}

DocumentDistributionType ::= SEQUENCE {
    printQualifier       PrintQualifier,
    maximumCopiesNumeric MaximumCopiesNumeric,
    party                Party
}

DocumentReferenceType ::= SEQUENCE {
    iD         ID-1,
    copyIndicator CopyIndicator OPTIONAL,
    uUID       UUID OPTIONAL,
    issueDate  IssueDate OPTIONAL,
    issueTime  IssueTime OPTIONAL,
    documentTypeCode DocumentTypeCode OPTIONAL,
    documentType DocumentType OPTIONAL,
    xPath-list SEQUENCE OF xPath XPath,
    languageID LanguageID OPTIONAL,
    localeCode LocaleCode OPTIONAL,
    versionID  VersionID OPTIONAL,
    documentStatusCode DocumentStatusCode OPTIONAL,
    documentDescription-list SEQUENCE OF documentDescription 
	DocumentDescription,
    attachment Attachment OPTIONAL,
    validityPeriod ValidityPeriod OPTIONAL,
    issuerParty IssuerParty OPTIONAL,
    resultOfVerification ResultOfVerification OPTIONAL
}

DocumentResponseType ::= SEQUENCE {
    response        Response,
    documentReference-list SEQUENCE (SIZE(1..MAX)) OF documentReference 
	DocumentReference,
    issuerParty     IssuerParty OPTIONAL,
    recipientParty  RecipientParty OPTIONAL,
    lineResponse-list SEQUENCE OF lineResponse LineResponse
}

DutyType ::= SEQUENCE {
    amount      Amount,
    duty        Duty-1 OPTIONAL,
    dutyCode    DutyCode OPTIONAL,
    taxCategory TaxCategory OPTIONAL
}

EconomicOperatorShortListType ::= SEQUENCE {
    limitationDescription-list SEQUENCE OF limitationDescription 
	LimitationDescription,
    expectedQuantity     ExpectedQuantity OPTIONAL,
    maximumQuantity      MaximumQuantity OPTIONAL,
    minimumQuantity      MinimumQuantity OPTIONAL,
    preSelectedParty-list SEQUENCE OF preSelectedParty PreSelectedParty
}

EndorsementType ::= SEQUENCE {
    documentID     DocumentID,
    approvalStatus ApprovalStatus,
    remarks-list   SEQUENCE OF remarks Remarks,
    endorserParty  EndorserParty,
    signature-list SEQUENCE OF signature Signature-1
}

EndorserPartyType ::= SEQUENCE {
    roleCode         RoleCode,
    sequenceNumeric  SequenceNumeric,
    party            Party,
    signatoryContact SignatoryContact
}

EnergyTaxReportType ::= SEQUENCE {
    taxEnergyAmount  TaxEnergyAmount OPTIONAL,
    taxEnergyOnAccountAmount TaxEnergyOnAccountAmount OPTIONAL,
    taxEnergyBalanceAmount TaxEnergyBalanceAmount OPTIONAL,
    taxScheme        TaxScheme
}

EnergyWaterSupplyType ::= SEQUENCE {
    consumptionReport-list     SEQUENCE OF consumptionReport ConsumptionReport
	,
    energyTaxReport-list       SEQUENCE OF energyTaxReport EnergyTaxReport,
    consumptionAverage-list    SEQUENCE OF consumptionAverage 
	ConsumptionAverage,
    energyWaterCorrection-list SEQUENCE OF energyWaterCorrection 
	EnergyWaterCorrection
}

EnvironmentalEmissionType ::= SEQUENCE {
    environmentalEmissionTypeCode EnvironmentalEmissionTypeCode,
    valueMeasure         ValueMeasure,
    description-list     SEQUENCE OF description Description
}

EvaluationCriteriaType ::= SEQUENCE {
    evaluationCriteriaTypeCode EvaluationCriteriaTypeCode OPTIONAL,
    description-list     SEQUENCE OF description Description,
    thresholdAmount      ThresholdAmount OPTIONAL,
    thresholdQuantity    ThresholdQuantity OPTIONAL,
    expressionCode-list  SEQUENCE OF expressionCode ExpressionCode,
    durationPeriod       DurationPeriod OPTIONAL,
    suggestedEvidence-list SEQUENCE OF suggestedEvidence SuggestedEvidence
}

EventType ::= SEQUENCE {
    identificationID    IdentificationID OPTIONAL,
    occurrenceDate      OccurrenceDate OPTIONAL,
    occurrenceTime      OccurrenceTime OPTIONAL,
    typeCode            TypeCode OPTIONAL,
    description-list    SEQUENCE OF description Description,
    completionIndicator CompletionIndicator OPTIONAL,
    currentStatus-list  SEQUENCE OF currentStatus CurrentStatus,
    contact-list        SEQUENCE OF contact Contact,
    occurenceLocation   OccurenceLocation OPTIONAL
}

EventCommentType ::= SEQUENCE {
    comment   Comment,
    issueDate IssueDate OPTIONAL,
    issueTime IssueTime OPTIONAL
}

EventLineItemType ::= SEQUENCE {
    lineNumberNumeric    LineNumberNumeric OPTIONAL,
    participatingLocationsLocation ParticipatingLocationsLocation OPTIONAL,
    retailPlannedImpact-list SEQUENCE OF retailPlannedImpact 
	RetailPlannedImpact,
    supplyItem           SupplyItem
}

EventTacticType ::= SEQUENCE {
    comment        Comment OPTIONAL,
    quantity       Quantity OPTIONAL,
    eventTacticEnumeration EventTacticEnumeration,
    period         Period OPTIONAL
}

EventTacticEnumerationType ::= SEQUENCE {
    consumerIncentiveTacticTypeCode ConsumerIncentiveTacticTypeCode OPTIONAL,
    displayTacticTypeCode      DisplayTacticTypeCode OPTIONAL,
    featureTacticTypeCode      FeatureTacticTypeCode OPTIONAL,
    tradeItemPackingLabelingTypeCode TradeItemPackingLabelingTypeCode OPTIONAL
}

EvidenceType ::= SEQUENCE {
    iD                   ID-1 OPTIONAL,
    evidenceTypeCode     EvidenceTypeCode OPTIONAL,
    name-list            SEQUENCE OF name Name-1,
    evidenceIssuingParty EvidenceIssuingParty OPTIONAL,
    documentReference    DocumentReference OPTIONAL
}

ExceptionCriteriaLineType ::= SEQUENCE {
    iD         ID-1,
    note-list  SEQUENCE OF note Note,
    thresholdValueComparisonCode ThresholdValueComparisonCode,
    thresholdQuantity ThresholdQuantity,
    exceptionStatusCode ExceptionStatusCode OPTIONAL,
    collaborationPriorityCode CollaborationPriorityCode OPTIONAL,
    exceptionResolutionCode-list SEQUENCE OF exceptionResolutionCode 
	ExceptionResolutionCode,
    supplyChainActivityTypeCode SupplyChainActivityTypeCode OPTIONAL,
    performanceMetricTypeCode PerformanceMetricTypeCode OPTIONAL,
    effectivePeriod EffectivePeriod OPTIONAL,
    supplyItem-list SEQUENCE (SIZE(1..MAX)) OF supplyItem SupplyItem,
    forecastExceptionCriteriaLine ForecastExceptionCriteriaLine OPTIONAL
}

ExceptionNotificationLineType ::= SEQUENCE {
    iD         ID-1,
    note-list  SEQUENCE OF note Note,
    description Description OPTIONAL,
    exceptionStatusCode ExceptionStatusCode OPTIONAL,
    collaborationPriorityCode CollaborationPriorityCode OPTIONAL,
    resolutionCode ResolutionCode OPTIONAL,
    comparedValueMeasure ComparedValueMeasure,
    sourceValueMeasure SourceValueMeasure,
    varianceQuantity VarianceQuantity OPTIONAL,
    supplyChainActivityTypeCode SupplyChainActivityTypeCode OPTIONAL,
    performanceMetricTypeCode PerformanceMetricTypeCode OPTIONAL,
    exceptionObservationPeriod ExceptionObservationPeriod OPTIONAL,
    documentReference-list SEQUENCE OF documentReference DocumentReference,
    forecastException ForecastException OPTIONAL,
    supplyItem SupplyItem
}

ExchangeRateType ::= SEQUENCE {
    sourceCurrencyCode SourceCurrencyCode,
    sourceCurrencyBaseRate SourceCurrencyBaseRate OPTIONAL,
    targetCurrencyCode TargetCurrencyCode,
    targetCurrencyBaseRate TargetCurrencyBaseRate OPTIONAL,
    exchangeMarketID ExchangeMarketID OPTIONAL,
    calculationRate CalculationRate OPTIONAL,
    mathematicOperatorCode MathematicOperatorCode OPTIONAL,
    date          Date-1 OPTIONAL,
    foreignExchangeContract ForeignExchangeContract OPTIONAL
}

ExternalReferenceType ::= SEQUENCE {
    uRI         URI OPTIONAL,
    documentHash DocumentHash OPTIONAL,
    hashAlgorithmMethod-list SEQUENCE OF hashAlgorithmMethod 
	HashAlgorithmMethod,
    expiryDate  ExpiryDate OPTIONAL,
    expiryTime  ExpiryTime OPTIONAL,
    mimeCode    MimeCode OPTIONAL,
    formatCode  FormatCode OPTIONAL,
    encodingCode EncodingCode OPTIONAL,
    characterSetCode CharacterSetCode OPTIONAL,
    fileName    FileName OPTIONAL,
    description-list SEQUENCE OF description Description
}

FinancialAccountType ::= SEQUENCE {
    iD         ID-1 OPTIONAL,
    name       Name-1 OPTIONAL,
    aliasName  AliasName OPTIONAL,
    accountTypeCode AccountTypeCode OPTIONAL,
    accountFormatCode AccountFormatCode OPTIONAL,
    currencyCode CurrencyCode OPTIONAL,
    paymentNote-list SEQUENCE OF paymentNote PaymentNote,
    financialInstitutionBranch FinancialInstitutionBranch OPTIONAL,
    country    Country OPTIONAL
}

FinancialGuaranteeType ::= SEQUENCE {
    guaranteeTypeCode  GuaranteeTypeCode,
    description-list   SEQUENCE OF description Description,
    liabilityAmount    LiabilityAmount OPTIONAL,
    amountRate         AmountRate OPTIONAL,
    constitutionPeriod ConstitutionPeriod OPTIONAL
}

FinancialInstitutionType ::= SEQUENCE {
    iD      ID-1 OPTIONAL,
    name    Name-1 OPTIONAL,
    address Address OPTIONAL
}

ForecastExceptionType ::= SEQUENCE {
    forecastPurposeCode ForecastPurposeCode,
    forecastTypeCode   ForecastTypeCode,
    issueDate          IssueDate,
    issueTime          IssueTime OPTIONAL,
    dataSourceCode     DataSourceCode,
    comparisonDataCode ComparisonDataCode OPTIONAL,
    comparisonForecastIssueTime ComparisonForecastIssueTime OPTIONAL,
    comparisonForecastIssueDate ComparisonForecastIssueDate OPTIONAL
}

ForecastExceptionCriteriaLineType ::= SEQUENCE {
    forecastPurposeCode ForecastPurposeCode,
    forecastTypeCode    ForecastTypeCode,
    comparisonDataSourceCode ComparisonDataSourceCode OPTIONAL,
    dataSourceCode      DataSourceCode,
    timeDeltaDaysQuantity TimeDeltaDaysQuantity OPTIONAL
}

ForecastLineType ::= SEQUENCE {
    iD         ID-1,
    note-list  SEQUENCE OF note Note,
    frozenDocumentIndicator FrozenDocumentIndicator OPTIONAL,
    forecastTypeCode ForecastTypeCode,
    forecastPeriod ForecastPeriod OPTIONAL,
    salesItem  SalesItem OPTIONAL
}

ForecastRevisionLineType ::= SEQUENCE {
    iD         ID-1,
    note-list  SEQUENCE OF note Note,
    description Description OPTIONAL,
    revisedForecastLineID RevisedForecastLineID,
    sourceForecastIssueDate SourceForecastIssueDate,
    sourceForecastIssueTime SourceForecastIssueTime,
    adjustmentReasonCode AdjustmentReasonCode OPTIONAL,
    forecastPeriod ForecastPeriod OPTIONAL,
    salesItem  SalesItem OPTIONAL
}

FrameworkAgreementType ::= SEQUENCE {
    expectedOperatorQuantity ExpectedOperatorQuantity OPTIONAL,
    maximumOperatorQuantity MaximumOperatorQuantity OPTIONAL,
    justification-list     SEQUENCE OF justification Justification,
    frequency-list         SEQUENCE OF frequency Frequency,
    durationPeriod         DurationPeriod OPTIONAL,
    subsequentProcessTenderRequirement-list SEQUENCE OF 
	subsequentProcessTenderRequirement SubsequentProcessTenderRequirement
}

GoodsItemType ::= SEQUENCE {
    iD         ID-1 OPTIONAL,
    sequenceNumberID SequenceNumberID OPTIONAL,
    description-list SEQUENCE OF description Description,
    hazardousRiskIndicator HazardousRiskIndicator OPTIONAL,
    declaredCustomsValueAmount DeclaredCustomsValueAmount OPTIONAL,
    declaredForCarriageValueAmount DeclaredForCarriageValueAmount OPTIONAL,
    declaredStatisticsValueAmount DeclaredStatisticsValueAmount OPTIONAL,
    freeOnBoardValueAmount FreeOnBoardValueAmount OPTIONAL,
    insuranceValueAmount InsuranceValueAmount OPTIONAL,
    valueAmount ValueAmount OPTIONAL,
    grossWeightMeasure GrossWeightMeasure OPTIONAL,
    netWeightMeasure NetWeightMeasure OPTIONAL,
    netNetWeightMeasure NetNetWeightMeasure OPTIONAL,
    chargeableWeightMeasure ChargeableWeightMeasure OPTIONAL,
    grossVolumeMeasure GrossVolumeMeasure OPTIONAL,
    netVolumeMeasure NetVolumeMeasure OPTIONAL,
    quantity   Quantity OPTIONAL,
    preferenceCriterionCode PreferenceCriterionCode OPTIONAL,
    requiredCustomsID RequiredCustomsID OPTIONAL,
    customsStatusCode CustomsStatusCode OPTIONAL,
    customsTariffQuantity CustomsTariffQuantity OPTIONAL,
    customsImportClassifiedIndicator CustomsImportClassifiedIndicator OPTIONAL
	,
    chargeableQuantity ChargeableQuantity OPTIONAL,
    returnableQuantity ReturnableQuantity OPTIONAL,
    item-list  SEQUENCE OF item Item,
    goodsItemContainer-list SEQUENCE OF goodsItemContainer GoodsItemContainer,
    freightAllowanceCharge-list SEQUENCE OF freightAllowanceCharge 
	FreightAllowanceCharge,
    invoiceLine-list SEQUENCE OF invoiceLine InvoiceLine,
    temperature-list SEQUENCE OF temperature Temperature,
    containedGoodsItem-list SEQUENCE OF containedGoodsItem ContainedGoodsItem,
    originAddress OriginAddress OPTIONAL,
    delivery   Delivery OPTIONAL,
    pickup     Pickup OPTIONAL,
    despatch   Despatch OPTIONAL,
    measurementDimension-list SEQUENCE OF measurementDimension 
	MeasurementDimension,
    containingPackage-list SEQUENCE OF containingPackage ContainingPackage,
    shipmentDocumentReference ShipmentDocumentReference OPTIONAL
}

GoodsItemContainerType ::= SEQUENCE {
    iD         ID-1,
    quantity   Quantity OPTIONAL,
    transportEquipment-list SEQUENCE OF transportEquipment TransportEquipment
}

HazardousGoodsTransitType ::= SEQUENCE {
    transportEmergencyCardCode TransportEmergencyCardCode OPTIONAL,
    packingCriteriaCode    PackingCriteriaCode OPTIONAL,
    hazardousRegulationCode HazardousRegulationCode OPTIONAL,
    inhalationToxicityZoneCode InhalationToxicityZoneCode OPTIONAL,
    transportAuthorizationCode TransportAuthorizationCode OPTIONAL,
    maximumTemperature     MaximumTemperature OPTIONAL,
    minimumTemperature     MinimumTemperature OPTIONAL
}

HazardousItemType ::= SEQUENCE {
    iD         ID-1 OPTIONAL,
    placardNotation PlacardNotation OPTIONAL,
    placardEndorsement PlacardEndorsement OPTIONAL,
    additionalInformation AdditionalInformation OPTIONAL,
    uNDGCode   UNDGCode OPTIONAL,
    emergencyProceduresCode EmergencyProceduresCode OPTIONAL,
    medicalFirstAidGuideCode MedicalFirstAidGuideCode OPTIONAL,
    technicalName TechnicalName OPTIONAL,
    categoryName CategoryName OPTIONAL,
    hazardousCategoryCode HazardousCategoryCode OPTIONAL,
    upperOrangeHazardPlacardID UpperOrangeHazardPlacardID OPTIONAL,
    lowerOrangeHazardPlacardID LowerOrangeHazardPlacardID OPTIONAL,
    markingID  MarkingID OPTIONAL,
    hazardClassID HazardClassID OPTIONAL,
    netWeightMeasure NetWeightMeasure OPTIONAL,
    netVolumeMeasure NetVolumeMeasure OPTIONAL,
    quantity   Quantity OPTIONAL,
    contactParty ContactParty OPTIONAL,
    secondaryHazard-list SEQUENCE OF secondaryHazard SecondaryHazard,
    hazardousGoodsTransit-list SEQUENCE OF hazardousGoodsTransit 
	HazardousGoodsTransit,
    emergencyTemperature EmergencyTemperature OPTIONAL,
    flashpointTemperature FlashpointTemperature OPTIONAL,
    additionalTemperature-list SEQUENCE OF additionalTemperature 
	AdditionalTemperature
}

ImmobilizedSecurityType ::= SEQUENCE {
    immobilizationCertificateID ImmobilizationCertificateID OPTIONAL,
    securityID         SecurityID OPTIONAL,
    issueDate          IssueDate OPTIONAL,
    faceValueAmount    FaceValueAmount OPTIONAL,
    marketValueAmount  MarketValueAmount OPTIONAL,
    sharesNumberQuantity SharesNumberQuantity OPTIONAL,
    issuerParty        IssuerParty OPTIONAL
}

InstructionForReturnsLineType ::= SEQUENCE {
    iD                ID-1,
    note-list         SEQUENCE OF note Note,
    quantity          Quantity,
    manufacturerParty ManufacturerParty OPTIONAL,
    item              Item
}

InventoryReportLineType ::= SEQUENCE {
    iD           ID-1,
    note-list    SEQUENCE OF note Note,
    quantity     Quantity,
    inventoryValueAmount InventoryValueAmount OPTIONAL,
    availabilityDate AvailabilityDate OPTIONAL,
    availabilityStatusCode AvailabilityStatusCode OPTIONAL,
    item         Item
}

InvoiceLineType ::= SEQUENCE {
    iD         ID-1,
    uUID       UUID OPTIONAL,
    note-list  SEQUENCE OF note Note,
    invoicedQuantity InvoicedQuantity OPTIONAL,
    lineExtensionAmount LineExtensionAmount,
    taxPointDate TaxPointDate OPTIONAL,
    accountingCostCode AccountingCostCode OPTIONAL,
    accountingCost AccountingCost OPTIONAL,
    paymentPurposeCode PaymentPurposeCode OPTIONAL,
    freeOfChargeIndicator FreeOfChargeIndicator OPTIONAL,
    invoicePeriod-list SEQUENCE OF invoicePeriod InvoicePeriod,
    orderLineReference-list SEQUENCE OF orderLineReference OrderLineReference,
    despatchLineReference-list SEQUENCE OF despatchLineReference 
	DespatchLineReference,
    receiptLineReference-list SEQUENCE OF receiptLineReference 
	ReceiptLineReference,
    billingReference-list SEQUENCE OF billingReference BillingReference,
    documentReference-list SEQUENCE OF documentReference DocumentReference,
    pricingReference PricingReference OPTIONAL,
    originatorParty OriginatorParty OPTIONAL,
    delivery-list SEQUENCE OF delivery Delivery,
    paymentTerms-list SEQUENCE OF paymentTerms PaymentTerms,
    allowanceCharge-list SEQUENCE OF allowanceCharge AllowanceCharge,
    taxTotal-list SEQUENCE OF taxTotal TaxTotal,
    item       Item,
    price      Price OPTIONAL,
    deliveryTerms DeliveryTerms OPTIONAL,
    subInvoiceLine-list SEQUENCE OF subInvoiceLine SubInvoiceLine
}

ItemType ::= SEQUENCE {
    description-list SEQUENCE OF description Description,
    packQuantity PackQuantity OPTIONAL,
    packSizeNumeric PackSizeNumeric OPTIONAL,
    catalogueIndicator CatalogueIndicator OPTIONAL,
    name         Name-1 OPTIONAL,
    hazardousRiskIndicator HazardousRiskIndicator OPTIONAL,
    additionalInformation AdditionalInformation OPTIONAL,
    keyword-list SEQUENCE OF keyword Keyword,
    brandName-list SEQUENCE OF brandName BrandName,
    modelName-list SEQUENCE OF modelName ModelName,
    buyersItemIdentification BuyersItemIdentification OPTIONAL,
    sellersItemIdentification SellersItemIdentification OPTIONAL,
    manufacturersItemIdentification-list SEQUENCE OF 
	manufacturersItemIdentification ManufacturersItemIdentification,
    standardItemIdentification StandardItemIdentification OPTIONAL,
    catalogueItemIdentification CatalogueItemIdentification OPTIONAL,
    additionalItemIdentification-list SEQUENCE OF additionalItemIdentification
	AdditionalItemIdentification,
    catalogueDocumentReference CatalogueDocumentReference OPTIONAL,
    itemSpecificationDocumentReference-list SEQUENCE OF 
	itemSpecificationDocumentReference ItemSpecificationDocumentReference,
    originCountry OriginCountry OPTIONAL,
    commodityClassification-list SEQUENCE OF commodityClassification 
	CommodityClassification,
    transactionConditions-list SEQUENCE OF transactionConditions 
	TransactionConditions,
    hazardousItem-list SEQUENCE OF hazardousItem HazardousItem,
    classifiedTaxCategory-list SEQUENCE OF classifiedTaxCategory 
	ClassifiedTaxCategory,
    additionalItemProperty-list SEQUENCE OF additionalItemProperty 
	AdditionalItemProperty,
    manufacturerParty-list SEQUENCE OF manufacturerParty ManufacturerParty,
    informationContentProviderParty InformationContentProviderParty OPTIONAL,
    originAddress-list SEQUENCE OF originAddress OriginAddress,
    itemInstance-list SEQUENCE OF itemInstance ItemInstance,
    certificate-list SEQUENCE OF certificate Certificate,
    dimension-list SEQUENCE OF dimension Dimension
}

ItemComparisonType ::= SEQUENCE {
    priceAmount PriceAmount OPTIONAL,
    quantity    Quantity OPTIONAL
}

ItemIdentificationType ::= SEQUENCE {
    iD         ID-1,
    extendedID ExtendedID OPTIONAL,
    physicalAttribute-list SEQUENCE OF physicalAttribute PhysicalAttribute,
    measurementDimension-list SEQUENCE OF measurementDimension 
	MeasurementDimension,
    issuerParty IssuerParty OPTIONAL
}

ItemInformationRequestLineType ::= SEQUENCE {
    timeFrequencyCode   TimeFrequencyCode OPTIONAL,
    supplyChainActivityTypeCode SupplyChainActivityTypeCode OPTIONAL,
    forecastTypeCode    ForecastTypeCode OPTIONAL,
    performanceMetricTypeCode PerformanceMetricTypeCode OPTIONAL,
    period-list         SEQUENCE (SIZE(1..MAX)) OF period Period,
    salesItem-list      SEQUENCE (SIZE(1..MAX)) OF salesItem SalesItem
}

ItemInstanceType ::= SEQUENCE {
    productTraceID    ProductTraceID OPTIONAL,
    manufactureDate   ManufactureDate OPTIONAL,
    manufactureTime   ManufactureTime OPTIONAL,
    bestBeforeDate    BestBeforeDate OPTIONAL,
    registrationID    RegistrationID OPTIONAL,
    serialID          SerialID OPTIONAL,
    additionalItemProperty-list SEQUENCE OF additionalItemProperty 
	AdditionalItemProperty,
    lotIdentification LotIdentification OPTIONAL
}

ItemLocationQuantityType ::= SEQUENCE {
    leadTimeMeasure LeadTimeMeasure OPTIONAL,
    minimumQuantity MinimumQuantity OPTIONAL,
    maximumQuantity MaximumQuantity OPTIONAL,
    hazardousRiskIndicator HazardousRiskIndicator OPTIONAL,
    tradingRestrictions-list SEQUENCE OF tradingRestrictions 
	TradingRestrictions,
    applicableTerritoryAddress-list SEQUENCE OF applicableTerritoryAddress 
	ApplicableTerritoryAddress,
    price         Price OPTIONAL,
    deliveryUnit-list SEQUENCE OF deliveryUnit DeliveryUnit,
    applicableTaxCategory-list SEQUENCE OF applicableTaxCategory 
	ApplicableTaxCategory,
    package       Package OPTIONAL,
    allowanceCharge-list SEQUENCE OF allowanceCharge AllowanceCharge,
    dependentPriceReference DependentPriceReference OPTIONAL
}

ItemManagementProfileType ::= SEQUENCE {
    frozenPeriodDaysNumeric FrozenPeriodDaysNumeric OPTIONAL,
    minimumInventoryQuantity MinimumInventoryQuantity OPTIONAL,
    multipleOrderQuantity MultipleOrderQuantity OPTIONAL,
    orderIntervalDaysNumeric OrderIntervalDaysNumeric OPTIONAL,
    replenishmentOwnerDescription ReplenishmentOwnerDescription OPTIONAL,
    targetServicePercent TargetServicePercent OPTIONAL,
    targetInventoryQuantity TargetInventoryQuantity OPTIONAL,
    effectivePeriod EffectivePeriod,
    item         Item,
    itemLocationQuantity ItemLocationQuantity OPTIONAL
}

ItemPropertyType ::= SEQUENCE {
    iD           ID-1 OPTIONAL,
    name         Name-1,
    nameCode     NameCode OPTIONAL,
    testMethod   TestMethod OPTIONAL,
    value        Value OPTIONAL,
    valueQuantity ValueQuantity OPTIONAL,
    valueQualifier-list SEQUENCE OF valueQualifier ValueQualifier,
    importanceCode ImportanceCode OPTIONAL,
    listValue-list SEQUENCE OF listValue ListValue,
    usabilityPeriod UsabilityPeriod OPTIONAL,
    itemPropertyGroup-list SEQUENCE OF itemPropertyGroup ItemPropertyGroup,
    rangeDimension RangeDimension OPTIONAL,
    itemPropertyRange ItemPropertyRange OPTIONAL
}

ItemPropertyGroupType ::= SEQUENCE {
    iD             ID-1,
    name           Name-1 OPTIONAL,
    importanceCode ImportanceCode OPTIONAL
}

ItemPropertyRangeType ::= SEQUENCE {
    minimumValue MinimumValue OPTIONAL,
    maximumValue MaximumValue OPTIONAL
}

LanguageType ::= SEQUENCE {
    iD         ID-1 OPTIONAL,
    name       Name-1 OPTIONAL,
    localeCode LocaleCode OPTIONAL
}

LineItemType ::= SEQUENCE {
    iD         ID-1,
    salesOrderID SalesOrderID OPTIONAL,
    uUID       UUID OPTIONAL,
    note-list  SEQUENCE OF note Note,
    lineStatusCode LineStatusCode OPTIONAL,
    quantity   Quantity OPTIONAL,
    lineExtensionAmount LineExtensionAmount OPTIONAL,
    totalTaxAmount TotalTaxAmount OPTIONAL,
    minimumQuantity MinimumQuantity OPTIONAL,
    maximumQuantity MaximumQuantity OPTIONAL,
    minimumBackorderQuantity MinimumBackorderQuantity OPTIONAL,
    maximumBackorderQuantity MaximumBackorderQuantity OPTIONAL,
    inspectionMethodCode InspectionMethodCode OPTIONAL,
    partialDeliveryIndicator PartialDeliveryIndicator OPTIONAL,
    backOrderAllowedIndicator BackOrderAllowedIndicator OPTIONAL,
    accountingCostCode AccountingCostCode OPTIONAL,
    accountingCost AccountingCost OPTIONAL,
    warrantyInformation-list SEQUENCE OF warrantyInformation 
	WarrantyInformation,
    delivery-list SEQUENCE OF delivery Delivery,
    deliveryTerms DeliveryTerms OPTIONAL,
    originatorParty OriginatorParty OPTIONAL,
    orderedShipment-list SEQUENCE OF orderedShipment OrderedShipment,
    pricingReference PricingReference OPTIONAL,
    allowanceCharge-list SEQUENCE OF allowanceCharge AllowanceCharge,
    price      Price OPTIONAL,
    item       Item,
    subLineItem-list SEQUENCE OF subLineItem SubLineItem,
    warrantyValidityPeriod WarrantyValidityPeriod OPTIONAL,
    warrantyParty WarrantyParty OPTIONAL
}

LineReferenceType ::= SEQUENCE {
    lineID            LineID,
    uUID              UUID OPTIONAL,
    lineStatusCode    LineStatusCode OPTIONAL,
    documentReference DocumentReference OPTIONAL
}

LineResponseType ::= SEQUENCE {
    lineReference LineReference,
    response-list SEQUENCE (SIZE(1..MAX)) OF response Response
}

LocationType ::= SEQUENCE {
    iD         ID-1 OPTIONAL,
    description Description OPTIONAL,
    conditions Conditions OPTIONAL,
    countrySubentity CountrySubentity OPTIONAL,
    countrySubentityCode CountrySubentityCode OPTIONAL,
    locationTypeCode LocationTypeCode OPTIONAL,
    informationURI InformationURI OPTIONAL,
    validityPeriod-list SEQUENCE OF validityPeriod ValidityPeriod,
    address    Address OPTIONAL,
    subsidiaryLocation-list SEQUENCE OF subsidiaryLocation SubsidiaryLocation,
    locationCoordinate-list SEQUENCE OF locationCoordinate LocationCoordinate
}

LocationCoordinateType ::= SEQUENCE {
    coordinateSystemCode CoordinateSystemCode OPTIONAL,
    latitudeDegreesMeasure LatitudeDegreesMeasure OPTIONAL,
    latitudeMinutesMeasure LatitudeMinutesMeasure OPTIONAL,
    latitudeDirectionCode LatitudeDirectionCode OPTIONAL,
    longitudeDegreesMeasure LongitudeDegreesMeasure OPTIONAL,
    longitudeMinutesMeasure LongitudeMinutesMeasure OPTIONAL,
    longitudeDirectionCode LongitudeDirectionCode OPTIONAL,
    altitudeMeasure     AltitudeMeasure OPTIONAL
}

LotIdentificationType ::= SEQUENCE {
    lotNumberID        LotNumberID OPTIONAL,
    expiryDate         ExpiryDate OPTIONAL,
    additionalItemProperty-list SEQUENCE OF additionalItemProperty 
	AdditionalItemProperty
}

MaritimeTransportType ::= SEQUENCE {
    vesselID   VesselID OPTIONAL,
    vesselName VesselName OPTIONAL
}

MeterType ::= SEQUENCE {
    meterNumber     MeterNumber OPTIONAL,
    meterName       MeterName OPTIONAL,
    meterConstant   MeterConstant OPTIONAL,
    meterConstantCode MeterConstantCode OPTIONAL,
    totalDeliveredQuantity TotalDeliveredQuantity OPTIONAL,
    meterReading-list SEQUENCE OF meterReading MeterReading,
    meterProperty-list SEQUENCE OF meterProperty MeterProperty
}

MeterPropertyType ::= SEQUENCE {
    name                Name-1 OPTIONAL,
    nameCode            NameCode OPTIONAL,
    value-list          SEQUENCE OF value Value,
    valueQuantity       ValueQuantity OPTIONAL,
    valueQualifier-list SEQUENCE OF valueQualifier ValueQualifier
}

MeterReadingType ::= SEQUENCE {
    meterReadingType     MeterReadingType-1 OPTIONAL,
    meterReadingTypeCode MeterReadingTypeCode OPTIONAL,
    previousMeterReadingDate PreviousMeterReadingDate,
    previousMeterQuantity PreviousMeterQuantity,
    latestMeterReadingDate LatestMeterReadingDate,
    latestMeterQuantity  LatestMeterQuantity,
    meterReadingMethod   MeterReadingMethod OPTIONAL,
    meterReadingMethodCode MeterReadingMethodCode OPTIONAL,
    meterReadingComments-list SEQUENCE OF meterReadingComments 
	MeterReadingComments,
    deliveredQuantity    DeliveredQuantity
}

MiscellaneousEventType ::= SEQUENCE {
    miscellaneousEventTypeCode MiscellaneousEventTypeCode,
    eventLineItem-list     SEQUENCE (SIZE(1..MAX)) OF eventLineItem 
	EventLineItem
}

MonetaryTotalType ::= SEQUENCE {
    lineExtensionAmount LineExtensionAmount OPTIONAL,
    taxExclusiveAmount TaxExclusiveAmount OPTIONAL,
    taxInclusiveAmount TaxInclusiveAmount OPTIONAL,
    allowanceTotalAmount AllowanceTotalAmount OPTIONAL,
    chargeTotalAmount  ChargeTotalAmount OPTIONAL,
    prepaidAmount      PrepaidAmount OPTIONAL,
    payableRoundingAmount PayableRoundingAmount OPTIONAL,
    payableAmount      PayableAmount,
    payableAlternativeAmount PayableAlternativeAmount OPTIONAL
}

NotificationRequirementType ::= SEQUENCE {
    notificationTypeCode NotificationTypeCode,
    notifyParty-list     SEQUENCE OF notifyParty NotifyParty,
    preEventPeriod       PreEventPeriod OPTIONAL,
    postEventPeriod      PostEventPeriod OPTIONAL
}

OnAccountPaymentType ::= SEQUENCE {
    estimatedConsumedQuantity EstimatedConsumedQuantity,
    note         Note OPTIONAL,
    paymentTerms-list SEQUENCE (SIZE(1..MAX)) OF paymentTerms PaymentTerms
}

OrderLineType ::= SEQUENCE {
    substitutionStatusCode SubstitutionStatusCode OPTIONAL,
    note-list        SEQUENCE OF note Note,
    lineItem         LineItem,
    sellerProposedSubstituteLineItem-list SEQUENCE OF 
	sellerProposedSubstituteLineItem SellerProposedSubstituteLineItem,
    sellerSubstitutedLineItem-list SEQUENCE OF sellerSubstitutedLineItem 
	SellerSubstitutedLineItem,
    buyerProposedSubstituteLineItem-list SEQUENCE OF 
	buyerProposedSubstituteLineItem BuyerProposedSubstituteLineItem,
    catalogueLineReference CatalogueLineReference OPTIONAL,
    quotationLineReference QuotationLineReference OPTIONAL,
    documentReference-list SEQUENCE OF documentReference DocumentReference
}

OrderLineReferenceType ::= SEQUENCE {
    lineID           LineID,
    salesOrderLineID SalesOrderLineID OPTIONAL,
    uUID             UUID OPTIONAL,
    lineStatusCode   LineStatusCode OPTIONAL,
    orderReference   OrderReference OPTIONAL
}

OrderReferenceType ::= SEQUENCE {
    iD                ID-1,
    salesOrderID      SalesOrderID OPTIONAL,
    copyIndicator     CopyIndicator OPTIONAL,
    uUID              UUID OPTIONAL,
    issueDate         IssueDate OPTIONAL,
    issueTime         IssueTime OPTIONAL,
    customerReference CustomerReference OPTIONAL,
    orderTypeCode     OrderTypeCode OPTIONAL,
    documentReference DocumentReference OPTIONAL
}

OrderedShipmentType ::= SEQUENCE {
    shipment     Shipment,
    package-list SEQUENCE OF package Package
}

PackageType ::= SEQUENCE {
    iD         ID-1 OPTIONAL,
    quantity   Quantity OPTIONAL,
    returnableMaterialIndicator ReturnableMaterialIndicator OPTIONAL,
    packageLevelCode PackageLevelCode OPTIONAL,
    packagingTypeCode PackagingTypeCode OPTIONAL,
    packingMaterial-list SEQUENCE OF packingMaterial PackingMaterial,
    traceID    TraceID OPTIONAL,
    containedPackage-list SEQUENCE OF containedPackage ContainedPackage,
    containingTransportEquipment ContainingTransportEquipment OPTIONAL,
    goodsItem-list SEQUENCE OF goodsItem GoodsItem,
    measurementDimension-list SEQUENCE OF measurementDimension 
	MeasurementDimension,
    deliveryUnit-list SEQUENCE OF deliveryUnit DeliveryUnit,
    delivery   Delivery OPTIONAL,
    pickup     Pickup OPTIONAL,
    despatch   Despatch OPTIONAL
}

PartyType ::= SEQUENCE {
    markCareIndicator MarkCareIndicator OPTIONAL,
    markAttentionIndicator MarkAttentionIndicator OPTIONAL,
    websiteURI       WebsiteURI OPTIONAL,
    logoReferenceID  LogoReferenceID OPTIONAL,
    endpointID       EndpointID OPTIONAL,
    industryClassificationCode IndustryClassificationCode OPTIONAL,
    partyIdentification-list SEQUENCE OF partyIdentification 
	PartyIdentification,
    partyName-list   SEQUENCE OF partyName PartyName,
    language         Language-1 OPTIONAL,
    postalAddress    PostalAddress OPTIONAL,
    physicalLocation PhysicalLocation OPTIONAL,
    partyTaxScheme-list SEQUENCE OF partyTaxScheme PartyTaxScheme,
    partyLegalEntity-list SEQUENCE OF partyLegalEntity PartyLegalEntity,
    contact          Contact OPTIONAL,
    person-list      SEQUENCE OF person Person,
    agentParty       AgentParty OPTIONAL,
    serviceProviderParty-list SEQUENCE OF serviceProviderParty 
	ServiceProviderParty,
    powerOfAttorney-list SEQUENCE OF powerOfAttorney PowerOfAttorney,
    financialAccount FinancialAccount OPTIONAL
}

PartyIdentificationType ::= SEQUENCE {
    iD ID-1
}

PartyLegalEntityType ::= SEQUENCE {
    registrationName   RegistrationName OPTIONAL,
    companyID          CompanyID OPTIONAL,
    registrationDate   RegistrationDate OPTIONAL,
    registrationExpirationDate RegistrationExpirationDate OPTIONAL,
    companyLegalFormCode CompanyLegalFormCode OPTIONAL,
    soleProprietorshipIndicator SoleProprietorshipIndicator OPTIONAL,
    companyLiquidationStatusCode CompanyLiquidationStatusCode OPTIONAL,
    corporateStockAmount CorporateStockAmount OPTIONAL,
    fullyPaidSharesIndicator FullyPaidSharesIndicator OPTIONAL,
    registrationAddress RegistrationAddress OPTIONAL,
    corporateRegistrationScheme CorporateRegistrationScheme OPTIONAL,
    headParty          HeadParty OPTIONAL,
    shareholderParty-list SEQUENCE OF shareholderParty ShareholderParty
}

PartyNameType ::= SEQUENCE {
    name Name-1
}

PartyTaxSchemeType ::= SEQUENCE {
    registrationName    RegistrationName OPTIONAL,
    companyID           CompanyID OPTIONAL,
    taxLevelCode        TaxLevelCode OPTIONAL,
    exemptionReasonCode ExemptionReasonCode OPTIONAL,
    exemptionReason     ExemptionReason OPTIONAL,
    registrationAddress RegistrationAddress OPTIONAL,
    taxScheme           TaxScheme
}

PaymentType ::= SEQUENCE {
    iD            ID-1 OPTIONAL,
    paidAmount    PaidAmount OPTIONAL,
    receivedDate  ReceivedDate OPTIONAL,
    paidDate      PaidDate OPTIONAL,
    paidTime      PaidTime OPTIONAL,
    instructionID InstructionID OPTIONAL
}

PaymentMandateType ::= SEQUENCE {
    iD         ID-1 OPTIONAL,
    mandateTypeCode MandateTypeCode OPTIONAL,
    clause-list SEQUENCE OF clause Clause,
    clauseCode-list SEQUENCE OF clauseCode ClauseCode,
    maximumPaymentInstructionsNumeric MaximumPaymentInstructionsNumeric
	OPTIONAL,
    maximumPaidAmount MaximumPaidAmount OPTIONAL,
    signatureID SignatureID OPTIONAL,
    payerParty PayerParty OPTIONAL,
    payerFinancialAccount PayerFinancialAccount OPTIONAL,
    validityPeriod ValidityPeriod OPTIONAL,
    paymentReversalPeriod PaymentReversalPeriod OPTIONAL
}

PaymentMeansType ::= SEQUENCE {
    iD          ID-1 OPTIONAL,
    paymentMeansCode PaymentMeansCode,
    paymentDueDate PaymentDueDate OPTIONAL,
    paymentChannelCode PaymentChannelCode OPTIONAL,
    instructionID InstructionID OPTIONAL,
    instructionNote-list SEQUENCE OF instructionNote InstructionNote,
    paymentID-list SEQUENCE OF paymentID PaymentID,
    cardAccount CardAccount OPTIONAL,
    payerFinancialAccount PayerFinancialAccount OPTIONAL,
    payeeFinancialAccount PayeeFinancialAccount OPTIONAL,
    creditAccount CreditAccount OPTIONAL,
    paymentMandate PaymentMandate OPTIONAL,
    tradeFinancing TradeFinancing OPTIONAL
}

PaymentTermsType ::= SEQUENCE {
    iD         ID-1 OPTIONAL,
    paymentMeansID-list SEQUENCE OF paymentMeansID PaymentMeansID,
    prepaidPaymentReferenceID PrepaidPaymentReferenceID OPTIONAL,
    note-list  SEQUENCE OF note Note,
    referenceEventCode ReferenceEventCode OPTIONAL,
    settlementDiscountPercent SettlementDiscountPercent OPTIONAL,
    penaltySurchargePercent PenaltySurchargePercent OPTIONAL,
    paymentPercent PaymentPercent OPTIONAL,
    amount     Amount OPTIONAL,
    settlementDiscountAmount SettlementDiscountAmount OPTIONAL,
    penaltyAmount PenaltyAmount OPTIONAL,
    paymentTermsDetailsURI PaymentTermsDetailsURI OPTIONAL,
    paymentDueDate PaymentDueDate OPTIONAL,
    installmentDueDate InstallmentDueDate OPTIONAL,
    invoicingPartyReference InvoicingPartyReference OPTIONAL,
    settlementPeriod SettlementPeriod OPTIONAL,
    penaltyPeriod PenaltyPeriod OPTIONAL,
    exchangeRate ExchangeRate OPTIONAL,
    validityPeriod ValidityPeriod OPTIONAL
}

PerformanceDataLineType ::= SEQUENCE {
    iD         ID-1,
    note-list  SEQUENCE OF note Note,
    performanceValueQuantity PerformanceValueQuantity,
    performanceMetricTypeCode PerformanceMetricTypeCode,
    period     Period OPTIONAL,
    item       Item OPTIONAL
}

PeriodType ::= SEQUENCE {
    startDate            StartDate OPTIONAL,
    startTime            StartTime OPTIONAL,
    endDate              EndDate OPTIONAL,
    endTime              EndTime OPTIONAL,
    durationMeasure      DurationMeasure OPTIONAL,
    descriptionCode-list SEQUENCE OF descriptionCode DescriptionCode,
    description-list     SEQUENCE OF description Description
}

PersonType ::= SEQUENCE {
    iD         ID-1 OPTIONAL,
    firstName  FirstName OPTIONAL,
    familyName FamilyName OPTIONAL,
    title      Title OPTIONAL,
    middleName MiddleName OPTIONAL,
    nameSuffix NameSuffix OPTIONAL,
    jobTitle   JobTitle OPTIONAL,
    nationalityID NationalityID OPTIONAL,
    genderCode GenderCode OPTIONAL,
    birthDate  BirthDate OPTIONAL,
    organizationDepartment OrganizationDepartment OPTIONAL,
    contact    Contact OPTIONAL,
    financialAccount FinancialAccount OPTIONAL,
    identityDocumentReference IdentityDocumentReference OPTIONAL
}

PhysicalAttributeType ::= SEQUENCE {
    attributeID      AttributeID,
    positionCode     PositionCode OPTIONAL,
    descriptionCode  DescriptionCode OPTIONAL,
    description-list SEQUENCE OF description Description
}

PickupType ::= SEQUENCE {
    iD                 ID-1 OPTIONAL,
    actualPickupDate   ActualPickupDate OPTIONAL,
    actualPickupTime   ActualPickupTime OPTIONAL,
    earliestPickupDate EarliestPickupDate OPTIONAL,
    earliestPickupTime EarliestPickupTime OPTIONAL,
    latestPickupDate   LatestPickupDate OPTIONAL,
    latestPickupTime   LatestPickupTime OPTIONAL,
    pickupLocation     PickupLocation OPTIONAL,
    pickupParty        PickupParty OPTIONAL
}

PowerOfAttorneyType ::= SEQUENCE {
    iD         ID-1 OPTIONAL,
    issueDate  IssueDate OPTIONAL,
    issueTime  IssueTime OPTIONAL,
    description-list SEQUENCE OF description Description,
    notaryParty NotaryParty,
    agentParty AgentParty,
    mandateDocumentReference-list SEQUENCE OF mandateDocumentReference 
	MandateDocumentReference
}

PriceType ::= SEQUENCE {
    priceAmount      PriceAmount,
    baseQuantity     BaseQuantity OPTIONAL,
    priceChangeReason-list SEQUENCE OF priceChangeReason PriceChangeReason,
    priceTypeCode    PriceTypeCode OPTIONAL,
    priceType        PriceType-1 OPTIONAL,
    orderableUnitFactorRate OrderableUnitFactorRate OPTIONAL,
    validityPeriod-list SEQUENCE OF validityPeriod ValidityPeriod,
    priceList        PriceList OPTIONAL,
    allowanceCharge-list SEQUENCE OF allowanceCharge AllowanceCharge,
    pricingExchangeRate PricingExchangeRate OPTIONAL
}

PriceListType ::= SEQUENCE {
    iD                  ID-1 OPTIONAL,
    statusCode          StatusCode OPTIONAL,
    validityPeriod-list SEQUENCE OF validityPeriod ValidityPeriod,
    previousPriceList   PreviousPriceList OPTIONAL
}

PricingReferenceType ::= SEQUENCE {
    originalItemLocationQuantity   OriginalItemLocationQuantity OPTIONAL,
    alternativeConditionPrice-list SEQUENCE OF alternativeConditionPrice 
	AlternativeConditionPrice
}

ProcessJustificationType ::= SEQUENCE {
    previousCancellationReasonCode PreviousCancellationReasonCode OPTIONAL,
    processReasonCode       ProcessReasonCode OPTIONAL,
    processReason-list      SEQUENCE OF processReason ProcessReason,
    description-list        SEQUENCE OF description Description
}

ProcurementProjectType ::= SEQUENCE {
    iD         ID-1 OPTIONAL,
    name-list  SEQUENCE (SIZE(1..MAX)) OF name Name-1,
    description-list SEQUENCE OF description Description,
    procurementTypeCode ProcurementTypeCode OPTIONAL,
    procurementSubTypeCode ProcurementSubTypeCode OPTIONAL,
    qualityControlCode QualityControlCode OPTIONAL,
    requiredFeeAmount RequiredFeeAmount OPTIONAL,
    feeDescription-list SEQUENCE OF feeDescription FeeDescription,
    requestedDeliveryDate RequestedDeliveryDate OPTIONAL,
    estimatedOverallContractQuantity EstimatedOverallContractQuantity OPTIONAL
	,
    budgetAmount BudgetAmount OPTIONAL,
    requiredCommodityClassification-list SEQUENCE OF 
	requiredCommodityClassification RequiredCommodityClassification,
    realizedLocation-list SEQUENCE OF realizedLocation RealizedLocation,
    plannedPeriod PlannedPeriod OPTIONAL,
    contractExtension ContractExtension OPTIONAL,
    requestForTenderLine-list SEQUENCE OF requestForTenderLine 
	RequestForTenderLine
}

ProcurementProjectLotType ::= SEQUENCE {
    iD                 ID-1,
    tenderingTerms     TenderingTerms OPTIONAL,
    procurementProject ProcurementProject
}

PromotionalEventType ::= SEQUENCE {
    promotionalEventTypeCode PromotionalEventTypeCode,
    submissionDate        SubmissionDate OPTIONAL,
    firstShipmentAvailibilityDate FirstShipmentAvailibilityDate OPTIONAL,
    latestProposalAcceptanceDate LatestProposalAcceptanceDate OPTIONAL,
    promotionalSpecification-list SEQUENCE (SIZE(1..MAX)) OF 
	promotionalSpecification PromotionalSpecification
}

PromotionalEventLineItemType ::= SEQUENCE {
    amount        Amount,
    eventLineItem EventLineItem
}

PromotionalSpecificationType ::= SEQUENCE {
    specificationID        SpecificationID OPTIONAL,
    promotionalEventLineItem-list SEQUENCE (SIZE(1..MAX)) OF 
	promotionalEventLineItem PromotionalEventLineItem,
    eventTactic-list       SEQUENCE OF eventTactic EventTactic
}

QualificationResolutionType ::= SEQUENCE {
    admissionCode      AdmissionCode,
    procurementProjectLotID ProcurementProjectLotID OPTIONAL,
    exclusionReason-list SEQUENCE OF exclusionReason ExclusionReason,
    resolution-list    SEQUENCE OF resolution Resolution,
    resolutionDate     ResolutionDate,
    resolutionTime     ResolutionTime OPTIONAL
}

QualifyingPartyType ::= SEQUENCE {
    participationPercent ParticipationPercent OPTIONAL,
    personalSituation-list SEQUENCE OF personalSituation PersonalSituation,
    operatingYearsQuantity OperatingYearsQuantity OPTIONAL,
    employeeQuantity EmployeeQuantity OPTIONAL,
    businessClassificationEvidenceID BusinessClassificationEvidenceID OPTIONAL
	,
    businessIdentityEvidenceID BusinessIdentityEvidenceID OPTIONAL,
    businessClassificationScheme BusinessClassificationScheme OPTIONAL,
    technicalCapability-list SEQUENCE OF technicalCapability 
	TechnicalCapability,
    financialCapability-list SEQUENCE OF financialCapability 
	FinancialCapability,
    completedTask-list SEQUENCE OF completedTask CompletedTask,
    declaration-list SEQUENCE OF declaration Declaration,
    party         Party OPTIONAL
}

QuotationLineType ::= SEQUENCE {
    iD         ID-1 OPTIONAL,
    note-list  SEQUENCE OF note Note,
    quantity   Quantity OPTIONAL,
    lineExtensionAmount LineExtensionAmount OPTIONAL,
    totalTaxAmount TotalTaxAmount OPTIONAL,
    requestForQuotationLineID RequestForQuotationLineID OPTIONAL,
    documentReference-list SEQUENCE OF documentReference DocumentReference,
    lineItem   LineItem,
    sellerProposedSubstituteLineItem-list SEQUENCE OF 
	sellerProposedSubstituteLineItem SellerProposedSubstituteLineItem,
    alternativeLineItem-list SEQUENCE OF alternativeLineItem 
	AlternativeLineItem,
    requestLineReference RequestLineReference OPTIONAL
}

RailTransportType ::= SEQUENCE {
    trainID   TrainID,
    railCarID RailCarID OPTIONAL
}

ReceiptLineType ::= SEQUENCE {
    iD         ID-1,
    uUID       UUID OPTIONAL,
    note-list  SEQUENCE OF note Note,
    receivedQuantity ReceivedQuantity OPTIONAL,
    shortQuantity ShortQuantity OPTIONAL,
    shortageActionCode ShortageActionCode OPTIONAL,
    rejectedQuantity RejectedQuantity OPTIONAL,
    rejectReasonCode RejectReasonCode OPTIONAL,
    rejectReason RejectReason OPTIONAL,
    rejectActionCode RejectActionCode OPTIONAL,
    quantityDiscrepancyCode QuantityDiscrepancyCode OPTIONAL,
    oversupplyQuantity OversupplyQuantity OPTIONAL,
    receivedDate ReceivedDate OPTIONAL,
    timingComplaintCode TimingComplaintCode OPTIONAL,
    timingComplaint TimingComplaint OPTIONAL,
    orderLineReference OrderLineReference OPTIONAL,
    despatchLineReference-list SEQUENCE OF despatchLineReference 
	DespatchLineReference,
    documentReference-list SEQUENCE OF documentReference DocumentReference,
    item-list  SEQUENCE OF item Item,
    shipment-list SEQUENCE OF shipment Shipment
}

RegulationType ::= SEQUENCE {
    name-list      SEQUENCE (SIZE(1..MAX)) OF name Name-1,
    legalReference LegalReference OPTIONAL,
    ontologyURI    OntologyURI OPTIONAL
}

RelatedItemType ::= SEQUENCE {
    iD               ID-1 OPTIONAL,
    quantity         Quantity OPTIONAL,
    description-list SEQUENCE OF description Description
}

ReminderLineType ::= SEQUENCE {
    iD         ID-1,
    note-list  SEQUENCE OF note Note,
    uUID       UUID OPTIONAL,
    balanceBroughtForwardIndicator BalanceBroughtForwardIndicator OPTIONAL,
    debitLineAmount DebitLineAmount OPTIONAL,
    creditLineAmount CreditLineAmount OPTIONAL,
    accountingCostCode AccountingCostCode OPTIONAL,
    accountingCost AccountingCost OPTIONAL,
    penaltySurchargePercent PenaltySurchargePercent OPTIONAL,
    amount     Amount OPTIONAL,
    paymentPurposeCode PaymentPurposeCode OPTIONAL,
    reminderPeriod-list SEQUENCE OF reminderPeriod ReminderPeriod,
    billingReference-list SEQUENCE OF billingReference BillingReference,
    exchangeRate ExchangeRate OPTIONAL
}

RemittanceAdviceLineType ::= SEQUENCE {
    iD         ID-1,
    note-list  SEQUENCE OF note Note,
    uUID       UUID OPTIONAL,
    debitLineAmount DebitLineAmount OPTIONAL,
    creditLineAmount CreditLineAmount OPTIONAL,
    balanceAmount BalanceAmount OPTIONAL,
    paymentPurposeCode PaymentPurposeCode OPTIONAL,
    invoicingPartyReference InvoicingPartyReference OPTIONAL,
    accountingSupplierParty AccountingSupplierParty OPTIONAL,
    accountingCustomerParty AccountingCustomerParty OPTIONAL,
    buyerCustomerParty BuyerCustomerParty OPTIONAL,
    sellerSupplierParty SellerSupplierParty OPTIONAL,
    originatorCustomerParty OriginatorCustomerParty OPTIONAL,
    payeeParty PayeeParty OPTIONAL,
    invoicePeriod-list SEQUENCE OF invoicePeriod InvoicePeriod,
    billingReference-list SEQUENCE OF billingReference BillingReference,
    documentReference-list SEQUENCE OF documentReference DocumentReference,
    exchangeRate ExchangeRate OPTIONAL
}

RenewalType ::= SEQUENCE {
    amount Amount OPTIONAL,
    period Period OPTIONAL
}

RequestForQuotationLineType ::= SEQUENCE {
    iD         ID-1 OPTIONAL,
    uUID       UUID OPTIONAL,
    note-list  SEQUENCE OF note Note,
    optionalLineItemIndicator OptionalLineItemIndicator OPTIONAL,
    privacyCode PrivacyCode OPTIONAL,
    securityClassificationCode SecurityClassificationCode OPTIONAL,
    documentReference-list SEQUENCE OF documentReference DocumentReference,
    lineItem   LineItem
}

RequestForTenderLineType ::= SEQUENCE {
    iD         ID-1 OPTIONAL,
    uUID       UUID OPTIONAL,
    note-list  SEQUENCE OF note Note,
    quantity   Quantity OPTIONAL,
    minimumQuantity MinimumQuantity OPTIONAL,
    maximumQuantity MaximumQuantity OPTIONAL,
    maximumTaxExclusiveAmount MaximumTaxExclusiveAmount OPTIONAL,
    maximumTaxInclusiveAmount MaximumTaxInclusiveAmount OPTIONAL,
    documentReference-list SEQUENCE OF documentReference DocumentReference,
    deliveryPeriod-list SEQUENCE OF deliveryPeriod DeliveryPeriod,
    requiredItemLocationQuantity-list SEQUENCE OF requiredItemLocationQuantity
	RequiredItemLocationQuantity,
    warrantyValidityPeriod WarrantyValidityPeriod OPTIONAL,
    item       Item,
    subRequestForTenderLine-list SEQUENCE OF subRequestForTenderLine 
	SubRequestForTenderLine
}

ResponseType ::= SEQUENCE {
    referenceID      ReferenceID OPTIONAL,
    responseCode     ResponseCode OPTIONAL,
    description-list SEQUENCE OF description Description,
    effectiveDate    EffectiveDate OPTIONAL,
    effectiveTime    EffectiveTime OPTIONAL,
    status           Status OPTIONAL
}

ResultOfVerificationType ::= SEQUENCE {
    validatorID          ValidatorID OPTIONAL,
    validationResultCode ValidationResultCode OPTIONAL,
    validationDate       ValidationDate OPTIONAL,
    validationTime       ValidationTime OPTIONAL,
    validateProcess      ValidateProcess OPTIONAL,
    validateTool         ValidateTool OPTIONAL,
    validateToolVersion  ValidateToolVersion OPTIONAL,
    signatoryParty       SignatoryParty OPTIONAL
}

RetailPlannedImpactType ::= SEQUENCE {
    amount              Amount,
    forecastPurposeCode ForecastPurposeCode,
    forecastTypeCode    ForecastTypeCode,
    period              Period OPTIONAL
}

RoadTransportType ::= SEQUENCE {
    licensePlateID LicensePlateID
}

SalesItemType ::= SEQUENCE {
    quantity      Quantity,
    activityProperty-list SEQUENCE OF activityProperty ActivityProperty,
    taxExclusivePrice-list SEQUENCE OF taxExclusivePrice TaxExclusivePrice,
    taxInclusivePrice-list SEQUENCE OF taxInclusivePrice TaxInclusivePrice,
    item          Item
}

SecondaryHazardType ::= SEQUENCE {
    iD         ID-1 OPTIONAL,
    placardNotation PlacardNotation OPTIONAL,
    placardEndorsement PlacardEndorsement OPTIONAL,
    emergencyProceduresCode EmergencyProceduresCode OPTIONAL,
    extension  Extension OPTIONAL
}

ServicePointType ::= SEQUENCE {
    sequenceNumberID  SequenceNumberID,
    transportModeCode TransportModeCode OPTIONAL,
    remarks-list      SEQUENCE OF remarks Remarks,
    servicePointLocation ServicePointLocation OPTIONAL,
    transportMeans    TransportMeans OPTIONAL,
    plannedDeparturePeriod PlannedDeparturePeriod OPTIONAL,
    plannedArrivalPeriod PlannedArrivalPeriod OPTIONAL,
    despatchPeriod    DespatchPeriod OPTIONAL,
    deliveryPeriod    DeliveryPeriod OPTIONAL
}

ServiceProviderPartyType ::= SEQUENCE {
    iD               ID-1 OPTIONAL,
    serviceTypeCode  ServiceTypeCode OPTIONAL,
    serviceType-list SEQUENCE OF serviceType ServiceType,
    party            Party,
    sellerContact    SellerContact OPTIONAL
}

ShareholderPartyType ::= SEQUENCE {
    partecipationPercent PartecipationPercent OPTIONAL,
    party                Party OPTIONAL
}

ShipmentType ::= SEQUENCE {
    iD         ID-1,
    shippingPriorityLevelCode ShippingPriorityLevelCode OPTIONAL,
    handlingCode HandlingCode OPTIONAL,
    handlingInstructions HandlingInstructions OPTIONAL,
    information Information OPTIONAL,
    grossWeightMeasure GrossWeightMeasure OPTIONAL,
    netWeightMeasure NetWeightMeasure OPTIONAL,
    netNetWeightMeasure NetNetWeightMeasure OPTIONAL,
    grossVolumeMeasure GrossVolumeMeasure OPTIONAL,
    netVolumeMeasure NetVolumeMeasure OPTIONAL,
    totalGoodsItemQuantity TotalGoodsItemQuantity OPTIONAL,
    totalTransportHandlingUnitQuantity TotalTransportHandlingUnitQuantity
	OPTIONAL,
    insuranceValueAmount InsuranceValueAmount OPTIONAL,
    declaredCustomsValueAmount DeclaredCustomsValueAmount OPTIONAL,
    declaredForCarriageValueAmount DeclaredForCarriageValueAmount OPTIONAL,
    declaredStatisticsValueAmount DeclaredStatisticsValueAmount OPTIONAL,
    freeOnBoardValueAmount FreeOnBoardValueAmount OPTIONAL,
    specialInstructions-list SEQUENCE OF specialInstructions 
	SpecialInstructions,
    deliveryInstructions-list SEQUENCE OF deliveryInstructions 
	DeliveryInstructions,
    splitConsignmentIndicator SplitConsignmentIndicator OPTIONAL,
    consignmentQuantity ConsignmentQuantity OPTIONAL,
    consignment-list SEQUENCE (SIZE(1..MAX)) OF consignment Consignment,
    goodsItem-list SEQUENCE OF goodsItem GoodsItem,
    shipmentStage-list SEQUENCE OF shipmentStage ShipmentStage,
    delivery   Delivery OPTIONAL,
    transportHandlingUnit-list SEQUENCE OF transportHandlingUnit 
	TransportHandlingUnit,
    returnAddress ReturnAddress OPTIONAL,
    originAddress OriginAddress OPTIONAL,
    firstArrivalPortLocation FirstArrivalPortLocation OPTIONAL,
    lastExitPortLocation LastExitPortLocation OPTIONAL,
    exportCountry ExportCountry OPTIONAL,
    freightAllowanceCharge-list SEQUENCE OF freightAllowanceCharge 
	FreightAllowanceCharge
}

ShipmentStageType ::= SEQUENCE {
    iD         ID-1 OPTIONAL,
    transportModeCode TransportModeCode OPTIONAL,
    transportMeansTypeCode TransportMeansTypeCode OPTIONAL,
    transitDirectionCode TransitDirectionCode OPTIONAL,
    preCarriageIndicator PreCarriageIndicator,
    onCarriageIndicator OnCarriageIndicator,
    estimatedDeliveryDate EstimatedDeliveryDate OPTIONAL,
    estimatedDeliveryTime EstimatedDeliveryTime OPTIONAL,
    requiredDeliveryDate RequiredDeliveryDate OPTIONAL,
    requiredDeliveryTime RequiredDeliveryTime OPTIONAL,
    loadingSequenceID LoadingSequenceID OPTIONAL,
    successiveSequenceID SuccessiveSequenceID OPTIONAL,
    instructions Instructions OPTIONAL,
    demurrageInstructions DemurrageInstructions OPTIONAL,
    transitPeriod TransitPeriod OPTIONAL,
    carrierParty-list SEQUENCE OF carrierParty CarrierParty,
    transportMeans TransportMeans OPTIONAL,
    loadingPortLocation LoadingPortLocation OPTIONAL,
    unloadingPortLocation UnloadingPortLocation OPTIONAL,
    transshipPortLocation TransshipPortLocation OPTIONAL,
    loadingTransportEvent LoadingTransportEvent OPTIONAL,
    examinationTransportEvent ExaminationTransportEvent OPTIONAL,
    availabilityTransportEvent AvailabilityTransportEvent OPTIONAL,
    exportationTransportEvent ExportationTransportEvent OPTIONAL,
    dischargeTransportEvent DischargeTransportEvent OPTIONAL,
    warehousingTransportEvent WarehousingTransportEvent OPTIONAL,
    takeoverTransportEvent TakeoverTransportEvent OPTIONAL,
    optionalTakeoverTransportEvent OptionalTakeoverTransportEvent OPTIONAL,
    dropoffTransportEvent DropoffTransportEvent OPTIONAL,
    actualPickupTransportEvent ActualPickupTransportEvent OPTIONAL,
    deliveryTransportEvent DeliveryTransportEvent OPTIONAL,
    receiptTransportEvent ReceiptTransportEvent OPTIONAL,
    storageTransportEvent StorageTransportEvent OPTIONAL,
    acceptanceTransportEvent AcceptanceTransportEvent OPTIONAL,
    terminalOperatorParty TerminalOperatorParty OPTIONAL,
    customsAgentParty CustomsAgentParty OPTIONAL
}

SignatureType-1 ::= SEQUENCE {
    iD         ID-1,
    note-list  SEQUENCE OF note Note,
    validationDate ValidationDate OPTIONAL,
    validationTime ValidationTime OPTIONAL,
    validatorID ValidatorID OPTIONAL,
    canonicalizationMethod CanonicalizationMethod-1 OPTIONAL,
    signatureMethod SignatureMethod-1 OPTIONAL,
    signatoryParty SignatoryParty OPTIONAL,
    digitalSignatureAttachment DigitalSignatureAttachment OPTIONAL,
    originalDocumentReference OriginalDocumentReference OPTIONAL
}

StatementLineType ::= SEQUENCE {
    iD         ID-1,
    note-list  SEQUENCE OF note Note,
    uUID       UUID OPTIONAL,
    balanceBroughtForwardIndicator BalanceBroughtForwardIndicator OPTIONAL,
    debitLineAmount DebitLineAmount OPTIONAL,
    creditLineAmount CreditLineAmount OPTIONAL,
    balanceAmount BalanceAmount OPTIONAL,
    paymentPurposeCode PaymentPurposeCode OPTIONAL,
    paymentMeans PaymentMeans OPTIONAL,
    paymentTerms-list SEQUENCE OF paymentTerms PaymentTerms,
    buyerCustomerParty BuyerCustomerParty OPTIONAL,
    sellerSupplierParty SellerSupplierParty OPTIONAL,
    originatorCustomerParty OriginatorCustomerParty OPTIONAL,
    accountingCustomerParty AccountingCustomerParty OPTIONAL,
    accountingSupplierParty AccountingSupplierParty OPTIONAL,
    payeeParty PayeeParty OPTIONAL,
    invoicePeriod-list SEQUENCE OF invoicePeriod InvoicePeriod,
    billingReference-list SEQUENCE OF billingReference BillingReference,
    documentReference-list SEQUENCE OF documentReference DocumentReference,
    exchangeRate ExchangeRate OPTIONAL,
    allowanceCharge-list SEQUENCE OF allowanceCharge AllowanceCharge
}

StatusType ::= SEQUENCE {
    conditionCode    ConditionCode OPTIONAL,
    referenceDate    ReferenceDate OPTIONAL,
    referenceTime    ReferenceTime OPTIONAL,
    description-list SEQUENCE OF description Description,
    statusReasonCode StatusReasonCode OPTIONAL,
    statusReason-list SEQUENCE OF statusReason StatusReason,
    sequenceID       SequenceID OPTIONAL,
    text-list        SEQUENCE OF text Text,
    indicationIndicator IndicationIndicator OPTIONAL,
    percent          Percent OPTIONAL,
    conditionValueMeasure-list SEQUENCE OF conditionValueMeasure 
	ConditionValueMeasure,
    reliabilityPercent ReliabilityPercent OPTIONAL
}

StockAvailabilityReportLineType ::= SEQUENCE {
    iD           ID-1,
    note-list    SEQUENCE OF note Note,
    quantity     Quantity,
    valueAmount  ValueAmount OPTIONAL,
    availabilityDate AvailabilityDate OPTIONAL,
    availabilityStatusCode AvailabilityStatusCode OPTIONAL,
    item         Item
}

StowageType ::= SEQUENCE {
    locationID        LocationID OPTIONAL,
    location-list     SEQUENCE OF location Location-1,
    measurementDimension-list SEQUENCE OF measurementDimension 
	MeasurementDimension
}

SubcontractTermsType ::= SEQUENCE {
    rate         Rate OPTIONAL,
    unknownPriceIndicator UnknownPriceIndicator OPTIONAL,
    description-list SEQUENCE OF description Description,
    amount       Amount OPTIONAL
}

SubscriberConsumptionType ::= SEQUENCE {
    consumptionID    ConsumptionID OPTIONAL,
    specificationTypeCode SpecificationTypeCode OPTIONAL,
    note-list        SEQUENCE OF note Note,
    totalMeteredQuantity TotalMeteredQuantity OPTIONAL,
    subscriberParty  SubscriberParty OPTIONAL,
    utilityConsumptionPoint UtilityConsumptionPoint,
    onAccountPayment-list SEQUENCE OF onAccountPayment OnAccountPayment,
    consumption      Consumption OPTIONAL,
    supplierConsumption-list SEQUENCE OF supplierConsumption 
	SupplierConsumption
}

SupplierConsumptionType ::= SEQUENCE {
    description          Description OPTIONAL,
    utilitySupplierParty UtilitySupplierParty OPTIONAL,
    utilityCustomerParty UtilityCustomerParty OPTIONAL,
    consumption          Consumption,
    consumptionLine-list SEQUENCE (SIZE(1..MAX)) OF consumptionLine 
	ConsumptionLine
}

SupplierPartyType ::= SEQUENCE {
    customerAssignedAccountID CustomerAssignedAccountID OPTIONAL,
    additionalAccountID-list SEQUENCE OF additionalAccountID 
	AdditionalAccountID,
    dataSendingCapability DataSendingCapability OPTIONAL,
    party           Party OPTIONAL,
    despatchContact DespatchContact OPTIONAL,
    accountingContact AccountingContact OPTIONAL,
    sellerContact   SellerContact OPTIONAL
}

TaxCategoryType ::= SEQUENCE {
    iD           ID-1 OPTIONAL,
    name         Name-1 OPTIONAL,
    percent      Percent OPTIONAL,
    baseUnitMeasure BaseUnitMeasure OPTIONAL,
    perUnitAmount PerUnitAmount OPTIONAL,
    taxExemptionReasonCode TaxExemptionReasonCode OPTIONAL,
    taxExemptionReason TaxExemptionReason OPTIONAL,
    tierRange    TierRange OPTIONAL,
    tierRatePercent TierRatePercent OPTIONAL,
    taxScheme    TaxScheme
}

TaxSchemeType ::= SEQUENCE {
    iD         ID-1 OPTIONAL,
    name       Name-1 OPTIONAL,
    taxTypeCode TaxTypeCode OPTIONAL,
    currencyCode CurrencyCode OPTIONAL,
    jurisdictionRegionAddress-list SEQUENCE OF jurisdictionRegionAddress 
	JurisdictionRegionAddress
}

TaxSubtotalType ::= SEQUENCE {
    taxableAmount   TaxableAmount OPTIONAL,
    taxAmount       TaxAmount,
    calculationSequenceNumeric CalculationSequenceNumeric OPTIONAL,
    transactionCurrencyTaxAmount TransactionCurrencyTaxAmount OPTIONAL,
    percent         Percent OPTIONAL,
    baseUnitMeasure BaseUnitMeasure OPTIONAL,
    perUnitAmount   PerUnitAmount OPTIONAL,
    tierRange       TierRange OPTIONAL,
    tierRatePercent TierRatePercent OPTIONAL,
    taxCategory     TaxCategory
}

TaxTotalType ::= SEQUENCE {
    taxAmount            TaxAmount,
    roundingAmount       RoundingAmount OPTIONAL,
    taxEvidenceIndicator TaxEvidenceIndicator OPTIONAL,
    taxIncludedIndicator TaxIncludedIndicator OPTIONAL,
    taxSubtotal-list     SEQUENCE OF taxSubtotal TaxSubtotal
}

TelecommunicationsServiceType ::= SEQUENCE {
    iD         ID-1 OPTIONAL,
    callDate   CallDate,
    callTime   CallTime,
    serviceNumberCalled ServiceNumberCalled,
    telecommunicationsServiceCategory TelecommunicationsServiceCategory
	OPTIONAL,
    telecommunicationsServiceCategoryCode 
	TelecommunicationsServiceCategoryCode OPTIONAL,
    movieTitle MovieTitle OPTIONAL,
    roamingPartnerName-list SEQUENCE OF roamingPartnerName RoamingPartnerName,
    payPerView PayPerView OPTIONAL,
    quantity   Quantity OPTIONAL,
    telecommunicationsServiceCall TelecommunicationsServiceCall OPTIONAL,
    telecommunicationsServiceCallCode TelecommunicationsServiceCallCode
	OPTIONAL,
    callBaseAmount CallBaseAmount OPTIONAL,
    callExtensionAmount CallExtensionAmount OPTIONAL,
    price      Price OPTIONAL,
    country    Country OPTIONAL,
    exchangeRate-list SEQUENCE OF exchangeRate ExchangeRate,
    allowanceCharge-list SEQUENCE OF allowanceCharge AllowanceCharge,
    taxTotal-list SEQUENCE OF taxTotal TaxTotal,
    callDuty-list SEQUENCE OF callDuty CallDuty,
    timeDuty-list SEQUENCE OF timeDuty TimeDuty
}

TelecommunicationsSupplyType ::= SEQUENCE {
    telecommunicationsSupplyType TelecommunicationsSupplyType-1 OPTIONAL,
    telecommunicationsSupplyTypeCode TelecommunicationsSupplyTypeCode OPTIONAL
	,
    privacyCode         PrivacyCode,
    description         Description OPTIONAL,
    totalAmount         TotalAmount OPTIONAL,
    telecommunicationsSupplyLine-list SEQUENCE (SIZE(1..MAX)) OF 
	telecommunicationsSupplyLine TelecommunicationsSupplyLine
}

TelecommunicationsSupplyLineType ::= SEQUENCE {
    iD         ID-1,
    phoneNumber PhoneNumber,
    description Description OPTIONAL,
    lineExtensionAmount LineExtensionAmount OPTIONAL,
    exchangeRate-list SEQUENCE OF exchangeRate ExchangeRate,
    allowanceCharge-list SEQUENCE OF allowanceCharge AllowanceCharge,
    taxTotal-list SEQUENCE OF taxTotal TaxTotal,
    telecommunicationsService-list SEQUENCE (SIZE(1..MAX)) OF 
	telecommunicationsService TelecommunicationsService
}

TemperatureType ::= SEQUENCE {
    attributeID      AttributeID,
    measure          Measure,
    description-list SEQUENCE OF description Description
}

TenderLineType ::= SEQUENCE {
    iD         ID-1 OPTIONAL,
    note-list  SEQUENCE OF note Note,
    quantity   Quantity OPTIONAL,
    lineExtensionAmount LineExtensionAmount OPTIONAL,
    totalTaxAmount TotalTaxAmount OPTIONAL,
    orderableUnit-list SEQUENCE OF orderableUnit OrderableUnit,
    contentUnitQuantity ContentUnitQuantity OPTIONAL,
    orderQuantityIncrementNumeric OrderQuantityIncrementNumeric OPTIONAL,
    minimumOrderQuantity MinimumOrderQuantity OPTIONAL,
    maximumOrderQuantity MaximumOrderQuantity OPTIONAL,
    warrantyInformation-list SEQUENCE OF warrantyInformation 
	WarrantyInformation,
    packLevelCode PackLevelCode OPTIONAL,
    documentReference-list SEQUENCE OF documentReference DocumentReference,
    item       Item OPTIONAL,
    offeredItemLocationQuantity-list SEQUENCE OF offeredItemLocationQuantity 
	OfferedItemLocationQuantity,
    replacementRelatedItem-list SEQUENCE OF replacementRelatedItem 
	ReplacementRelatedItem,
    warrantyParty WarrantyParty OPTIONAL,
    warrantyValidityPeriod WarrantyValidityPeriod OPTIONAL,
    subTenderLine-list SEQUENCE OF subTenderLine SubTenderLine
}

TenderPreparationType ::= SEQUENCE {
    tenderEnvelopeID      TenderEnvelopeID,
    tenderEnvelopeTypeCode TenderEnvelopeTypeCode OPTIONAL,
    description-list      SEQUENCE OF description Description,
    openTenderID          OpenTenderID OPTIONAL,
    procurementProjectLotID-list SEQUENCE OF procurementProjectLotID 
	ProcurementProjectLotID,
    documentTenderRequirement-list SEQUENCE OF documentTenderRequirement 
	DocumentTenderRequirement
}

TenderRequirementType ::= SEQUENCE {
    name-list         SEQUENCE OF name Name-1,
    description-list  SEQUENCE OF description Description,
    templateDocumentReference TemplateDocumentReference OPTIONAL
}

TenderResultType ::= SEQUENCE {
    tenderResultCode  TenderResultCode OPTIONAL,
    description-list  SEQUENCE OF description Description,
    advertisementAmount AdvertisementAmount OPTIONAL,
    awardDate         AwardDate,
    awardTime         AwardTime OPTIONAL,
    receivedTenderQuantity ReceivedTenderQuantity OPTIONAL,
    lowerTenderAmount LowerTenderAmount OPTIONAL,
    higherTenderAmount HigherTenderAmount OPTIONAL,
    startDate         StartDate OPTIONAL,
    contract          Contract OPTIONAL,
    winningParty      WinningParty OPTIONAL,
    awardedTenderedProject AwardedTenderedProject OPTIONAL,
    contractFormalizationPeriod ContractFormalizationPeriod OPTIONAL,
    subcontractTerms-list SEQUENCE OF subcontractTerms SubcontractTerms
}

TenderedProjectType ::= SEQUENCE {
    procurementProjectLotID ProcurementProjectLotID OPTIONAL,
    variantID           VariantID OPTIONAL,
    feeAmount           FeeAmount OPTIONAL,
    feeDescription-list SEQUENCE OF feeDescription FeeDescription,
    taxTotal-list       SEQUENCE OF taxTotal TaxTotal,
    legalMonetaryTotal  LegalMonetaryTotal OPTIONAL,
    tenderLine-list     SEQUENCE OF tenderLine TenderLine,
    awardingCriteriaResponse-list SEQUENCE OF awardingCriteriaResponse 
	AwardingCriteriaResponse
}

TendererPartyQualificationType ::= SEQUENCE {
    interestedProcurementLotsID-list SEQUENCE OF interestedProcurementLotsID 
	InterestedProcurementLotsID,
    mainQualifyingParty       MainQualifyingParty,
    additionalQualifyingParty-list SEQUENCE OF additionalQualifyingParty 
	AdditionalQualifyingParty
}

TendererQualificationRequestType ::= SEQUENCE {
    legalForm-list         SEQUENCE OF legalForm LegalForm,
    personalSituation-list SEQUENCE OF personalSituation PersonalSituation,
    operatingYearsQuantity OperatingYearsQuantity OPTIONAL,
    employeeQuantity       EmployeeQuantity OPTIONAL,
    description-list       SEQUENCE OF description Description,
    requiredBusinessClassificationScheme-list SEQUENCE OF 
	requiredBusinessClassificationScheme 
	RequiredBusinessClassificationScheme,
    technicalEvaluationCriteria-list SEQUENCE OF technicalEvaluationCriteria 
	TechnicalEvaluationCriteria,
    financialEvaluationCriteria-list SEQUENCE OF financialEvaluationCriteria 
	FinancialEvaluationCriteria,
    specificTendererRequirement-list SEQUENCE OF specificTendererRequirement 
	SpecificTendererRequirement
}

TendererRequirementType ::= SEQUENCE {
    name-list          SEQUENCE OF name Name-1,
    tendererRequirementTypeCode TendererRequirementTypeCode OPTIONAL,
    description-list   SEQUENCE OF description Description,
    suggestedEvidence-list SEQUENCE OF suggestedEvidence SuggestedEvidence
}

TenderingProcessType ::= SEQUENCE {
    iD         ID-1 OPTIONAL,
    originalContractingSystemID OriginalContractingSystemID OPTIONAL,
    description-list SEQUENCE OF description Description,
    negotiationDescription-list SEQUENCE OF negotiationDescription 
	NegotiationDescription,
    procedureCode ProcedureCode OPTIONAL,
    urgencyCode UrgencyCode OPTIONAL,
    expenseCode ExpenseCode OPTIONAL,
    partPresentationCode PartPresentationCode OPTIONAL,
    contractingSystemCode ContractingSystemCode OPTIONAL,
    submissionMethodCode SubmissionMethodCode OPTIONAL,
    candidateReductionConstraintIndicator 
	CandidateReductionConstraintIndicator OPTIONAL,
    governmentAgreementConstraintIndicator 
	GovernmentAgreementConstraintIndicator OPTIONAL,
    documentAvailabilityPeriod DocumentAvailabilityPeriod OPTIONAL,
    tenderSubmissionDeadlinePeriod TenderSubmissionDeadlinePeriod OPTIONAL,
    invitationSubmissionPeriod InvitationSubmissionPeriod OPTIONAL,
    participationRequestReceptionPeriod ParticipationRequestReceptionPeriod
	OPTIONAL,
    noticeDocumentReference-list SEQUENCE OF noticeDocumentReference 
	NoticeDocumentReference,
    additionalDocumentReference-list SEQUENCE OF additionalDocumentReference 
	AdditionalDocumentReference,
    processJustification-list SEQUENCE OF processJustification 
	ProcessJustification,
    economicOperatorShortList EconomicOperatorShortList OPTIONAL,
    openTenderEvent-list SEQUENCE OF openTenderEvent OpenTenderEvent,
    auctionTerms AuctionTerms OPTIONAL,
    frameworkAgreement FrameworkAgreement OPTIONAL
}

TenderingTermsType ::= SEQUENCE {
    awardingMethodTypeCode AwardingMethodTypeCode OPTIONAL,
    priceEvaluationCode PriceEvaluationCode OPTIONAL,
    maximumVariantQuantity MaximumVariantQuantity OPTIONAL,
    variantConstraintIndicator VariantConstraintIndicator OPTIONAL,
    acceptedVariantsDescription-list SEQUENCE OF acceptedVariantsDescription 
	AcceptedVariantsDescription,
    priceRevisionFormulaDescription-list SEQUENCE OF 
	priceRevisionFormulaDescription PriceRevisionFormulaDescription,
    fundingProgramCode FundingProgramCode OPTIONAL,
    fundingProgram-list SEQUENCE OF fundingProgram FundingProgram,
    maximumAdvertisementAmount MaximumAdvertisementAmount OPTIONAL,
    note-list         SEQUENCE OF note Note,
    paymentFrequencyCode PaymentFrequencyCode OPTIONAL,
    economicOperatorRegistryURI EconomicOperatorRegistryURI OPTIONAL,
    penaltyClauses-list SEQUENCE OF penaltyClauses PenaltyClauses,
    requiredCurriculaIndicator RequiredCurriculaIndicator OPTIONAL,
    requiredFinancialGuarantee-list SEQUENCE OF requiredFinancialGuarantee 
	RequiredFinancialGuarantee,
    procurementLegislationDocumentReference 
	ProcurementLegislationDocumentReference OPTIONAL,
    fiscalLegislationDocumentReference FiscalLegislationDocumentReference
	OPTIONAL,
    environmentalLegislationDocumentReference 
	EnvironmentalLegislationDocumentReference OPTIONAL,
    employmentLegislationDocumentReference 
	EmploymentLegislationDocumentReference OPTIONAL,
    contractualDocumentReference-list SEQUENCE OF contractualDocumentReference
	ContractualDocumentReference,
    callForTenderDocumentReference CallForTenderDocumentReference OPTIONAL,
    warrantyValidityPeriod WarrantyValidityPeriod OPTIONAL,
    paymentTerms-list SEQUENCE OF paymentTerms PaymentTerms,
    tendererQualificationRequest TendererQualificationRequest OPTIONAL,
    allowedSubcontractTerms-list SEQUENCE OF allowedSubcontractTerms 
	AllowedSubcontractTerms,
    tenderPreparation-list SEQUENCE OF tenderPreparation TenderPreparation,
    contractExecutionRequirement-list SEQUENCE OF contractExecutionRequirement
	ContractExecutionRequirement,
    awardingTerms     AwardingTerms OPTIONAL,
    additionalInformationParty AdditionalInformationParty OPTIONAL,
    documentProviderParty DocumentProviderParty OPTIONAL,
    tenderRecipientParty TenderRecipientParty OPTIONAL,
    contractResponsibleParty ContractResponsibleParty OPTIONAL,
    tenderEvaluationParty-list SEQUENCE OF tenderEvaluationParty 
	TenderEvaluationParty,
    tenderValidityPeriod TenderValidityPeriod OPTIONAL,
    contractAcceptancePeriod ContractAcceptancePeriod OPTIONAL,
    appealTerms       AppealTerms OPTIONAL,
    language-list     SEQUENCE OF language Language-1,
    budgetAccountLine-list SEQUENCE OF budgetAccountLine BudgetAccountLine
}

TradeFinancingType ::= SEQUENCE {
    iD         ID-1 OPTIONAL,
    financingInstrumentCode FinancingInstrumentCode OPTIONAL,
    clauseCode-list SEQUENCE OF clauseCode ClauseCode,
    clause-list SEQUENCE OF clause Clause,
    contractDocumentReference ContractDocumentReference OPTIONAL,
    documentReference-list SEQUENCE OF documentReference DocumentReference,
    financingParty FinancingParty,
    financingFinancialAccount FinancingFinancialAccount OPTIONAL
}

TradingTermsType ::= SEQUENCE {
    information-list  SEQUENCE OF information Information,
    reference         Reference-1 OPTIONAL,
    applicableAddress ApplicableAddress OPTIONAL
}

TransactionConditionsType ::= SEQUENCE {
    iD           ID-1 OPTIONAL,
    actionCode   ActionCode OPTIONAL,
    description-list SEQUENCE OF description Description,
    documentReference-list SEQUENCE OF documentReference DocumentReference
}

TransportEquipmentType ::= SEQUENCE {
    iD         ID-1 OPTIONAL,
    referencedConsignmentID ReferencedConsignmentID OPTIONAL,
    transportEquipmentTypeCode TransportEquipmentTypeCode OPTIONAL,
    providerTypeCode ProviderTypeCode OPTIONAL,
    ownerTypeCode OwnerTypeCode OPTIONAL,
    sizeTypeCode SizeTypeCode OPTIONAL,
    dispositionCode DispositionCode OPTIONAL,
    fullnessIndicationCode FullnessIndicationCode OPTIONAL,
    refrigerationOnIndicator RefrigerationOnIndicator OPTIONAL,
    information Information OPTIONAL,
    returnabilityIndicator ReturnabilityIndicator OPTIONAL,
    legalStatusIndicator LegalStatusIndicator OPTIONAL,
    airFlowPercent AirFlowPercent OPTIONAL,
    humidityPercent HumidityPercent OPTIONAL,
    animalFoodApprovedIndicator AnimalFoodApprovedIndicator OPTIONAL,
    humanFoodApprovedIndicator HumanFoodApprovedIndicator OPTIONAL,
    dangerousGoodsApprovedIndicator DangerousGoodsApprovedIndicator OPTIONAL,
    refrigeratedIndicator RefrigeratedIndicator OPTIONAL,
    characteristics Characteristics OPTIONAL,
    damageRemarks DamageRemarks OPTIONAL,
    description Description OPTIONAL,
    specialTransportRequirments SpecialTransportRequirments OPTIONAL,
    grossWeightMeasure GrossWeightMeasure OPTIONAL,
    grossVolumeMeasure GrossVolumeMeasure OPTIONAL,
    tareWeightMeasure TareWeightMeasure OPTIONAL,
    trackingDeviceCode TrackingDeviceCode OPTIONAL,
    powerIndicator PowerIndicator OPTIONAL,
    traceID    TraceID OPTIONAL,
    measurementDimension-list SEQUENCE OF measurementDimension 
	MeasurementDimension,
    transportEquipmentSeal-list SEQUENCE OF transportEquipmentSeal 
	TransportEquipmentSeal,
    minimumTemperature MinimumTemperature OPTIONAL,
    maximumTemperature MaximumTemperature OPTIONAL,
    providerParty ProviderParty OPTIONAL,
    loadingProofParty LoadingProofParty OPTIONAL,
    supplierParty SupplierParty OPTIONAL,
    ownerParty OwnerParty OPTIONAL,
    operatingParty OperatingParty OPTIONAL,
    loadingLocation LoadingLocation OPTIONAL,
    unloadingLocation UnloadingLocation OPTIONAL,
    storageLocation StorageLocation OPTIONAL,
    positioningTransportEvent-list SEQUENCE OF positioningTransportEvent 
	PositioningTransportEvent,
    quarantineTransportEvent-list SEQUENCE OF quarantineTransportEvent 
	QuarantineTransportEvent,
    deliveryTransportEvent-list SEQUENCE OF deliveryTransportEvent 
	DeliveryTransportEvent,
    pickupTransportEvent-list SEQUENCE OF pickupTransportEvent 
	PickupTransportEvent,
    handlingTransportEvent-list SEQUENCE OF handlingTransportEvent 
	HandlingTransportEvent,
    loadingTransportEvent-list SEQUENCE OF loadingTransportEvent 
	LoadingTransportEvent,
    transportEvent-list SEQUENCE OF transportEvent TransportEvent,
    applicableTransportMeans ApplicableTransportMeans OPTIONAL,
    haulageTradingTerms-list SEQUENCE OF haulageTradingTerms 
	HaulageTradingTerms,
    hazardousGoodsTransit-list SEQUENCE OF hazardousGoodsTransit 
	HazardousGoodsTransit,
    packagedTransportHandlingUnit-list SEQUENCE OF 
	packagedTransportHandlingUnit PackagedTransportHandlingUnit,
    serviceAllowanceCharge-list SEQUENCE OF serviceAllowanceCharge 
	ServiceAllowanceCharge,
    freightAllowanceCharge-list SEQUENCE OF freightAllowanceCharge 
	FreightAllowanceCharge,
    attachedTransportEquipment-list SEQUENCE OF attachedTransportEquipment 
	AttachedTransportEquipment,
    goodsItem-list SEQUENCE OF goodsItem GoodsItem,
    delivery   Delivery OPTIONAL,
    containedInTransportEquipment-list SEQUENCE OF 
	containedInTransportEquipment ContainedInTransportEquipment,
    pickup     Pickup OPTIONAL,
    despatch   Despatch OPTIONAL,
    shipmentDocumentReference ShipmentDocumentReference OPTIONAL
}

TransportEquipmentSealType ::= SEQUENCE {
    iD                 ID-1,
    sealIssuerTypeCode SealIssuerTypeCode OPTIONAL,
    condition          Condition OPTIONAL,
    sealStatusCode     SealStatusCode OPTIONAL,
    sealingPartyType   SealingPartyType OPTIONAL
}

TransportEventType ::= SEQUENCE {
    identificationID IdentificationID OPTIONAL,
    occurrenceDate  OccurrenceDate OPTIONAL,
    occurrenceTime  OccurrenceTime OPTIONAL,
    transportEventTypeCode TransportEventTypeCode OPTIONAL,
    description     Description OPTIONAL,
    completionIndicator CompletionIndicator OPTIONAL,
    reportedShipment ReportedShipment OPTIONAL,
    currentStatus-list SEQUENCE (SIZE(1..MAX)) OF currentStatus CurrentStatus,
    contact-list    SEQUENCE OF contact Contact,
    location        Location OPTIONAL
}

TransportExecutionTermsType ::= SEQUENCE {
    transportUserSpecialTerms-list SEQUENCE OF transportUserSpecialTerms 
	TransportUserSpecialTerms,
    transportServiceProviderSpecialTerms-list SEQUENCE OF 
	transportServiceProviderSpecialTerms 
	TransportServiceProviderSpecialTerms,
    changeConditions-list SEQUENCE OF changeConditions ChangeConditions,
    paymentTerms         PaymentTerms,
    deliveryTerms-list   SEQUENCE OF deliveryTerms DeliveryTerms,
    bonusPaymentTerms    BonusPaymentTerms OPTIONAL,
    commissionPaymentTerms CommissionPaymentTerms OPTIONAL,
    penaltyPaymentTerms  PenaltyPaymentTerms OPTIONAL,
    environmentalEmission-list SEQUENCE OF environmentalEmission 
	EnvironmentalEmission,
    notificationRequirement-list SEQUENCE OF notificationRequirement 
	NotificationRequirement
}

TransportHandlingUnitType ::= SEQUENCE {
    iD         ID-1 OPTIONAL,
    transportHandlingUnitTypeCode TransportHandlingUnitTypeCode OPTIONAL,
    handlingCode HandlingCode OPTIONAL,
    handlingInstructions HandlingInstructions OPTIONAL,
    hazardousRiskIndicator HazardousRiskIndicator OPTIONAL,
    totalGoodsItemQuantity TotalGoodsItemQuantity OPTIONAL,
    totalPackageQuantity TotalPackageQuantity OPTIONAL,
    damageRemarks-list SEQUENCE OF damageRemarks DamageRemarks,
    shippingMarks-list SEQUENCE OF shippingMarks ShippingMarks,
    handlingUnitDespatchLine-list SEQUENCE OF handlingUnitDespatchLine 
	HandlingUnitDespatchLine,
    actualPackage-list SEQUENCE OF actualPackage ActualPackage,
    receivedHandlingUnitReceiptLine-list SEQUENCE OF 
	receivedHandlingUnitReceiptLine ReceivedHandlingUnitReceiptLine,
    transportEquipment-list SEQUENCE OF transportEquipment TransportEquipment,
    transportMeans-list SEQUENCE OF transportMeans TransportMeans,
    hazardousGoodsTransit-list SEQUENCE OF hazardousGoodsTransit 
	HazardousGoodsTransit,
    measurementDimension-list SEQUENCE OF measurementDimension 
	MeasurementDimension,
    minimumTemperature MinimumTemperature OPTIONAL,
    maximumTemperature MaximumTemperature OPTIONAL,
    goodsItem-list SEQUENCE OF goodsItem GoodsItem,
    floorSpaceMeasurementDimension FloorSpaceMeasurementDimension OPTIONAL,
    palletSpaceMeasurementDimension PalletSpaceMeasurementDimension OPTIONAL,
    shipmentDocumentReference-list SEQUENCE OF shipmentDocumentReference 
	ShipmentDocumentReference,
    status-list SEQUENCE OF status Status
}

TransportLocationType ::= SEQUENCE {
    plannedDeparturePeriod PlannedDeparturePeriod OPTIONAL,
    plannedArrivalPeriod PlannedArrivalPeriod OPTIONAL,
    estimatedDeparturePeriod EstimatedDeparturePeriod OPTIONAL,
    estimatedArrivalPeriod EstimatedArrivalPeriod OPTIONAL,
    actualDepartureTransportEvent ActualDepartureTransportEvent OPTIONAL,
    transportEvent   TransportEvent OPTIONAL,
    location         Location
}

TransportMeansType ::= SEQUENCE {
    journeyID       JourneyID OPTIONAL,
    registrationNationalityID RegistrationNationalityID OPTIONAL,
    registrationNationality-list SEQUENCE OF registrationNationality 
	RegistrationNationality,
    directionCode   DirectionCode OPTIONAL,
    transportMeansTypeCode TransportMeansTypeCode OPTIONAL,
    tradeServiceCode TradeServiceCode OPTIONAL,
    stowage         Stowage OPTIONAL,
    airTransport    AirTransport OPTIONAL,
    roadTransport   RoadTransport OPTIONAL,
    railTransport   RailTransport OPTIONAL,
    maritimeTransport MaritimeTransport OPTIONAL,
    ownerParty      OwnerParty OPTIONAL,
    operatorParty-list SEQUENCE OF operatorParty OperatorParty
}

TransportScheduleType ::= SEQUENCE {
    sequenceNumberID     SequenceNumberID,
    referenceDate        ReferenceDate,
    referenceTime        ReferenceTime,
    reliabilityPercent   ReliabilityPercent OPTIONAL,
    remarks-list         SEQUENCE OF remarks Remarks,
    statusLocation       StatusLocation,
    estimatedArrivalPeriod EstimatedArrivalPeriod OPTIONAL,
    estimatedDeparturePeriod EstimatedDeparturePeriod OPTIONAL,
    actualArrivalTransportEvent ActualArrivalTransportEvent OPTIONAL,
    actualDepartureTransportEvent ActualDepartureTransportEvent OPTIONAL
}

TransportStatusType ::= SEQUENCE {
    timeDeviationIndicator TimeDeviationIndicator,
    conditionDeviationIndicator ConditionDeviationIndicator,
    updatedDelivery        UpdatedDelivery OPTIONAL,
    updatedDespatch        UpdatedDespatch OPTIONAL,
    statusLocation         StatusLocation OPTIONAL,
    referencedTransportHandlingUnit-list SEQUENCE OF 
	referencedTransportHandlingUnit ReferencedTransportHandlingUnit
}

TransportationSegmentType ::= SEQUENCE {
    sequenceNumberID         SequenceNumberID,
    transportExecutionPlanReferenceID TransportExecutionPlanReferenceID,
    transportModeCode        TransportModeCode OPTIONAL,
    transportMeansTypeCode   TransportMeansTypeCode OPTIONAL,
    transportationService    TransportationService,
    transportServiceProviderParty TransportServiceProviderParty,
    carryingTransportEquipment CarryingTransportEquipment OPTIONAL,
    carryingPackage          CarryingPackage OPTIONAL,
    carryingTransportMeans   CarryingTransportMeans OPTIONAL,
    departureTransportLocation DepartureTransportLocation OPTIONAL,
    intermediateTransportLocation-list SEQUENCE OF 
	intermediateTransportLocation IntermediateTransportLocation,
    arrivalTransportLocation ArrivalTransportLocation OPTIONAL
}

TransportationServiceType ::= SEQUENCE {
    transportServiceCode TransportServiceCode,
    tariffClassCode  TariffClassCode OPTIONAL,
    priority         Priority OPTIONAL,
    freightRateClassCode FreightRateClassCode OPTIONAL,
    transportationServiceDescription TransportationServiceDescription OPTIONAL
	,
    transportationServiceDetailsURI TransportationServiceDetailsURI OPTIONAL,
    nominationDate   NominationDate OPTIONAL,
    nominationTime   NominationTime OPTIONAL
}

UnstructuredPriceType ::= SEQUENCE {
    priceAmount PriceAmount OPTIONAL,
    timeAmount  TimeAmount OPTIONAL
}

UtilityItemType ::= SEQUENCE {
    iD          ID-1,
    subscriberID SubscriberID OPTIONAL,
    subscriberIDType SubscriberIDType OPTIONAL,
    subscriberIDTypeCode SubscriberIDTypeCode OPTIONAL,
    description-list SEQUENCE OF description Description,
    packQuantity PackQuantity OPTIONAL,
    packSizeNumeric PackSizeNumeric OPTIONAL,
    consumptionType ConsumptionType-1 OPTIONAL,
    consumptionTypeCode ConsumptionTypeCode OPTIONAL,
    currentChargeType CurrentChargeType OPTIONAL,
    currentChargeTypeCode CurrentChargeTypeCode OPTIONAL,
    oneTimeChargeType OneTimeChargeType OPTIONAL,
    oneTimeChargeTypeCode OneTimeChargeTypeCode OPTIONAL,
    taxCategory TaxCategory OPTIONAL,
    contract    Contract OPTIONAL
}

WebSiteAccessType ::= SEQUENCE {
    uRI      URI OPTIONAL,
    password Password,
    login    Login
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:CommonAggregateComponents-2"
	PREFIX "cac"
    NAMESPACE ActivityDataLineType.iD, 
	ActivityDataLineType.supplyChainActivityTypeCode, 
	ActivityPropertyType.name, ActivityPropertyType.value, AddressType.iD,
	AddressType.addressTypeCode, AddressType.addressFormatCode, 
	AddressType.postbox, AddressType.floor, AddressType.room, 
	AddressType.streetName, AddressType.additionalStreetName, 
	AddressType.blockName, AddressType.buildingName, 
	AddressType.buildingNumber, AddressType.inhouseMail, 
	AddressType.department, AddressType.markAttention, 
	AddressType.markCare, AddressType.plotIdentification, 
	AddressType.citySubdivisionName, AddressType.cityName, 
	AddressType.postalZone, AddressType.countrySubentity, 
	AddressType.countrySubentityCode, AddressType.region, 
	AddressType.district, AddressType.timezoneOffset, 
	AddressLineType.line, AirTransportType.aircraftID, 
	AllowanceChargeType.iD, AllowanceChargeType.chargeIndicator, 
	AllowanceChargeType.allowanceChargeReasonCode, 
	AllowanceChargeType.allowanceChargeReason, 
	AllowanceChargeType.multiplierFactorNumeric, 
	AllowanceChargeType.prepaidIndicator, 
	AllowanceChargeType.sequenceNumeric, AllowanceChargeType.amount, 
	AllowanceChargeType.baseAmount, 
	AllowanceChargeType.accountingCostCode, 
	AllowanceChargeType.accountingCost, AllowanceChargeType.perUnitAmount,
	AppealTermsType.description-list.description, 
	AttachmentType.embeddedDocumentBinaryObject, 
	AuctionTermsType.auctionConstraintIndicator, 
	AuctionTermsType.justificationDescription-list.justificationDescription,
	AuctionTermsType.description-list.description, 
	AuctionTermsType.processDescription-list.processDescription, 
	AuctionTermsType.conditionsDescription-list.conditionsDescription, 
	AuctionTermsType.electronicDeviceDescription-list.electronicDeviceDescription,
	AuctionTermsType.auctionURI, AwardingCriteriaType.iD, 
	AwardingCriteriaType.awardingCriteriaTypeCode, 
	AwardingCriteriaType.description-list.description, 
	AwardingCriteriaType.weightNumeric, 
	AwardingCriteriaType.weight-list.weight, 
	AwardingCriteriaType.calculationExpression-list.calculationExpression,
	AwardingCriteriaType.calculationExpressionCode, 
	AwardingCriteriaType.minimumQuantity, 
	AwardingCriteriaType.maximumQuantity, 
	AwardingCriteriaType.minimumAmount, 
	AwardingCriteriaType.maximumAmount, 
	AwardingCriteriaType.minimumImprovementBid-list.minimumImprovementBid,
	AwardingCriteriaResponseType.iD, 
	AwardingCriteriaResponseType.awardingCriteriaID, 
	AwardingCriteriaResponseType.awardingCriteriaDescription-list.awardingCriteriaDescription,
	AwardingCriteriaResponseType.description-list.description, 
	AwardingCriteriaResponseType.quantity, 
	AwardingCriteriaResponseType.amount, 
	AwardingTermsType.weightingAlgorithmCode, 
	AwardingTermsType.description-list.description, 
	AwardingTermsType.technicalCommitteeDescription-list.technicalCommitteeDescription,
	AwardingTermsType.lowTendersDescription-list.lowTendersDescription, 
	BillingReferenceLineType.iD, BillingReferenceLineType.amount, 
	BranchType.iD, BranchType.name, BudgetAccountType.iD, 
	BudgetAccountType.budgetYearNumeric, BudgetAccountLineType.iD, 
	BudgetAccountLineType.totalAmount, 
	BudgetAmountType.estimatedOverallContractAmount, 
	BudgetAmountType.totalAmount, BudgetAmountType.taxExclusiveAmount, 
	BudgetAmountType.minimumAmount, 
	BudgetAmountType.monetaryScope-list.monetaryScope, 
	BudgetAmountType.averageSubsequentContractAmount, 
	CapabilityType.capabilityTypeCode, 
	CapabilityType.description-list.description, 
	CapabilityType.valueAmount, CapabilityType.valueQuantity, 
	CapabilityType.evidenceSuppliedID-list.evidenceSuppliedID, 
	CardAccountType.primaryAccountNumberID, CardAccountType.networkID, 
	CardAccountType.cardTypeCode, CardAccountType.validityStartDate, 
	CardAccountType.expiryDate, CardAccountType.issuerID, 
	CardAccountType.issueNumberID, CardAccountType.cV2ID, 
	CardAccountType.cardChipCode, CardAccountType.chipApplicationID, 
	CardAccountType.holderName, 
	CatalogueItemSpecificationUpdateLineType.iD, CatalogueLineType.iD, 
	CatalogueLineType.actionCode, CatalogueLineType.lifeCycleStatusCode, 
	CatalogueLineType.contractSubdivision, 
	CatalogueLineType.note-list.note, 
	CatalogueLineType.orderableIndicator, CatalogueLineType.orderableUnit,
	CatalogueLineType.contentUnitQuantity, 
	CatalogueLineType.orderQuantityIncrementNumeric, 
	CatalogueLineType.minimumOrderQuantity, 
	CatalogueLineType.maximumOrderQuantity, 
	CatalogueLineType.warrantyInformation-list.warrantyInformation, 
	CatalogueLineType.packLevelCode, CataloguePricingUpdateLineType.iD, 
	CatalogueReferenceType.iD, CatalogueReferenceType.uUID, 
	CatalogueReferenceType.issueDate, CatalogueReferenceType.issueTime, 
	CatalogueReferenceType.revisionDate, 
	CatalogueReferenceType.revisionTime, 
	CatalogueReferenceType.note-list.note, 
	CatalogueReferenceType.description-list.description, 
	CatalogueReferenceType.versionID, 
	CatalogueReferenceType.previousVersionID, CatalogueRequestLineType.iD,
	CatalogueRequestLineType.contractSubdivision, 
	CatalogueRequestLineType.note-list.note, CertificateType.iD, 
	CertificateType.certificateTypeCode, CertificateType.certificateType, 
	CertificateType.remarks, 
	CertificateOfOriginApplicationType.referenceID, 
	CertificateOfOriginApplicationType.certificateType, 
	CertificateOfOriginApplicationType.applicationStatusCode, 
	CertificateOfOriginApplicationType.originalJobID, 
	CertificateOfOriginApplicationType.previousJobID, 
	CertificateOfOriginApplicationType.remarks, 
	ClassificationCategoryType.name, ClassificationCategoryType.codeValue,
	ClassificationCategoryType.description-list.description, 
	ClassificationSchemeType.iD, ClassificationSchemeType.uUID, 
	ClassificationSchemeType.lastRevisionDate, 
	ClassificationSchemeType.lastRevisionTime, 
	ClassificationSchemeType.note-list.note, 
	ClassificationSchemeType.name, 
	ClassificationSchemeType.description-list.description, 
	ClassificationSchemeType.agencyID, 
	ClassificationSchemeType.agencyName, 
	ClassificationSchemeType.versionID, ClassificationSchemeType.uRI, 
	ClassificationSchemeType.schemeURI, 
	ClassificationSchemeType.languageID, 
	CommodityClassificationType.natureCode, 
	CommodityClassificationType.cargoTypeCode, 
	CommodityClassificationType.commodityCode, 
	CommodityClassificationType.itemClassificationCode, 
	CommunicationType.channelCode, CommunicationType.channel, 
	CommunicationType.value, CompletedTaskType.annualAverageAmount, 
	CompletedTaskType.totalTaskAmount, 
	CompletedTaskType.partyCapacityAmount, 
	CompletedTaskType.description-list.description, 
	CompletedTaskType.evidenceSuppliedID, ConsignmentType.iD, 
	ConsignmentType.carrierAssignedID, 
	ConsignmentType.consigneeAssignedID, 
	ConsignmentType.consignorAssignedID, 
	ConsignmentType.freightForwarderAssignedID, 
	ConsignmentType.brokerAssignedID, 
	ConsignmentType.contractedCarrierAssignedID, 
	ConsignmentType.performingCarrierAssignedID, 
	ConsignmentType.summaryDescription-list.summaryDescription, 
	ConsignmentType.totalInvoiceAmount, 
	ConsignmentType.declaredCustomsValueAmount, 
	ConsignmentType.tariffDescription-list.tariffDescription, 
	ConsignmentType.tariffCode, ConsignmentType.insurancePremiumAmount, 
	ConsignmentType.grossWeightMeasure, ConsignmentType.netWeightMeasure, 
	ConsignmentType.netNetWeightMeasure, 
	ConsignmentType.chargeableWeightMeasure, 
	ConsignmentType.grossVolumeMeasure, ConsignmentType.netVolumeMeasure, 
	ConsignmentType.loadingLengthMeasure, 
	ConsignmentType.remarks-list.remarks, 
	ConsignmentType.hazardousRiskIndicator, 
	ConsignmentType.animalFoodIndicator, 
	ConsignmentType.humanFoodIndicator, 
	ConsignmentType.livestockIndicator, 
	ConsignmentType.bulkCargoIndicator, 
	ConsignmentType.containerizedIndicator, 
	ConsignmentType.generalCargoIndicator, 
	ConsignmentType.specialSecurityIndicator, 
	ConsignmentType.thirdPartyPayerIndicator, 
	ConsignmentType.carrierServiceInstructions, 
	ConsignmentType.customsClearanceServiceInstructions, 
	ConsignmentType.forwarderServiceInstructions, 
	ConsignmentType.specialServiceInstructions, 
	ConsignmentType.sequenceID, ConsignmentType.shippingPriorityLevelCode,
	ConsignmentType.handlingCode, ConsignmentType.handlingInstructions, 
	ConsignmentType.information, ConsignmentType.totalGoodsItemQuantity, 
	ConsignmentType.totalTransportHandlingUnitQuantity, 
	ConsignmentType.insuranceValueAmount, 
	ConsignmentType.declaredForCarriageValueAmount, 
	ConsignmentType.declaredStatisticsValueAmount, 
	ConsignmentType.freeOnBoardValueAmount, 
	ConsignmentType.specialInstructions-list.specialInstructions, 
	ConsignmentType.splitConsignmentIndicator, 
	ConsignmentType.deliveryInstructions-list.deliveryInstructions, 
	ConsignmentType.consignmentQuantity, 
	ConsignmentType.consolidatableIndicator, 
	ConsignmentType.haulageInstructions-list.haulageInstructions, 
	ConsignmentType.loadingSequenceID, 
	ConsumptionType.utilityStatementTypeCode, 
	ConsumptionAverageType.averageAmount, 
	ConsumptionAverageType.description, 
	ConsumptionHistoryType.meterNumber, ConsumptionHistoryType.quantity, 
	ConsumptionHistoryType.amount, 
	ConsumptionHistoryType.consumptionLevelCode, 
	ConsumptionHistoryType.consumptionLevel, 
	ConsumptionHistoryType.description-list.description, 
	ConsumptionLineType.iD, 
	ConsumptionLineType.parentDocumentLineReferenceID, 
	ConsumptionLineType.invoicedQuantity, 
	ConsumptionLineType.lineExtensionAmount, ConsumptionPointType.iD, 
	ConsumptionPointType.description, ConsumptionPointType.subscriberID, 
	ConsumptionPointType.subscriberTypeIdentifier, 
	ConsumptionPointType.subscriberTypeCode, 
	ConsumptionPointType.totalDeliveredQuantity, ConsumptionReportType.iD,
	ConsumptionReportType.consumptionType, 
	ConsumptionReportType.consumptionTypeCode, 
	ConsumptionReportType.description-list.description, 
	ConsumptionReportType.totalConsumedQuantity, 
	ConsumptionReportType.basicConsumedQuantity, 
	ConsumptionReportType.residentOccupantsNumeric, 
	ConsumptionReportType.consumersEnergyLevelCode, 
	ConsumptionReportType.consumersEnergyLevel, 
	ConsumptionReportType.residenceType, 
	ConsumptionReportType.residenceTypeCode, 
	ConsumptionReportType.heatingType, 
	ConsumptionReportType.heatingTypeCode, 
	ConsumptionReportReferenceType.consumptionReportID, 
	ConsumptionReportReferenceType.consumptionType, 
	ConsumptionReportReferenceType.consumptionTypeCode, 
	ConsumptionReportReferenceType.totalConsumedQuantity, ContactType.iD, 
	ContactType.name, ContactType.telephone, ContactType.telefax, 
	ContactType.electronicMail, ContactType.note-list.note, 
	ContractType.iD, ContractType.issueDate, ContractType.issueTime, 
	ContractType.nominationDate, ContractType.nominationTime, 
	ContractType.contractTypeCode, ContractType.contractType, 
	ContractType.note-list.note, ContractType.versionID, 
	ContractType.description-list.description, 
	ContractExecutionRequirementType.name-list.name, 
	ContractExecutionRequirementType.executionRequirementCode, 
	ContractExecutionRequirementType.description-list.description, 
	ContractExtensionType.optionsDescription-list.optionsDescription, 
	ContractExtensionType.minimumNumberNumeric, 
	ContractExtensionType.maximumNumberNumeric, 
	ContractingPartyType.contractingPartyTypeCode, 
	ContractingPartyType.activityCode-list.activityCode, 
	ContractingPartyType.buyerProfileURI, 
	CorporateRegistrationSchemeType.iD, 
	CorporateRegistrationSchemeType.name, 
	CorporateRegistrationSchemeType.corporateRegistrationTypeCode, 
	CorrectionType.correctionType, CorrectionType.correctionTypeCode, 
	CorrectionType.meterNumber, CorrectionType.gasPressureQuantity, 
	CorrectionType.actualTemperatureReductionQuantity, 
	CorrectionType.normalTemperatureReductionQuantity, 
	CorrectionType.differenceTemperatureReductionQuantity, 
	CorrectionType.description, CorrectionType.correctionUnitAmount, 
	CorrectionType.consumptionEnergyQuantity, 
	CorrectionType.consumptionWaterQuantity, 
	CorrectionType.correctionAmount, CountryType.identificationCode, 
	CountryType.name, CreditAccountType.accountID, CreditNoteLineType.iD, 
	CreditNoteLineType.uUID, CreditNoteLineType.note-list.note, 
	CreditNoteLineType.creditedQuantity, 
	CreditNoteLineType.lineExtensionAmount, 
	CreditNoteLineType.taxPointDate, 
	CreditNoteLineType.accountingCostCode, 
	CreditNoteLineType.accountingCost, 
	CreditNoteLineType.paymentPurposeCode, 
	CreditNoteLineType.freeOfChargeIndicator, 
	CustomerPartyType.customerAssignedAccountID, 
	CustomerPartyType.supplierAssignedAccountID, 
	CustomerPartyType.additionalAccountID-list.additionalAccountID, 
	DebitNoteLineType.iD, DebitNoteLineType.uUID, 
	DebitNoteLineType.note-list.note, DebitNoteLineType.debitedQuantity, 
	DebitNoteLineType.lineExtensionAmount, DebitNoteLineType.taxPointDate,
	DebitNoteLineType.accountingCostCode, 
	DebitNoteLineType.accountingCost, 
	DebitNoteLineType.paymentPurposeCode, DeclarationType.name-list.name, 
	DeclarationType.declarationTypeCode, 
	DeclarationType.description-list.description, 
	DeclarationType.evidenceSuppliedID-list.evidenceSuppliedID, 
	DeliveryType.iD, DeliveryType.quantity, DeliveryType.minimumQuantity, 
	DeliveryType.maximumQuantity, DeliveryType.actualDeliveryDate, 
	DeliveryType.actualDeliveryTime, DeliveryType.latestDeliveryDate, 
	DeliveryType.latestDeliveryTime, DeliveryType.releaseID, 
	DeliveryType.trackingID, DeliveryTermsType.iD, 
	DeliveryTermsType.specialTerms, 
	DeliveryTermsType.lossRiskResponsibilityCode, 
	DeliveryTermsType.lossRisk, DeliveryTermsType.amount, 
	DeliveryUnitType.batchQuantity, DeliveryUnitType.consumerUnitQuantity,
	DeliveryUnitType.hazardousRiskIndicator, 
	DependentPriceReferenceType.percent, DespatchType.iD, 
	DespatchType.requestedDespatchDate, 
	DespatchType.requestedDespatchTime, 
	DespatchType.estimatedDespatchDate, 
	DespatchType.estimatedDespatchTime, DespatchType.actualDespatchDate, 
	DespatchType.actualDespatchTime, DespatchType.guaranteedDespatchDate, 
	DespatchType.guaranteedDespatchTime, DespatchType.releaseID, 
	DespatchType.instructions, DespatchLineType.iD, DespatchLineType.uUID,
	DespatchLineType.note-list.note, DespatchLineType.lineStatusCode, 
	DespatchLineType.deliveredQuantity, 
	DespatchLineType.backorderQuantity, DespatchLineType.backorderReason, 
	DespatchLineType.outstandingQuantity, 
	DespatchLineType.outstandingReason, 
	DespatchLineType.oversupplyQuantity, DimensionType.attributeID, 
	DimensionType.measure, DimensionType.description-list.description, 
	DimensionType.minimumMeasure, DimensionType.maximumMeasure, 
	DocumentDistributionType.printQualifier, 
	DocumentDistributionType.maximumCopiesNumeric, 
	DocumentReferenceType.iD, DocumentReferenceType.copyIndicator, 
	DocumentReferenceType.uUID, DocumentReferenceType.issueDate, 
	DocumentReferenceType.issueTime, 
	DocumentReferenceType.documentTypeCode, 
	DocumentReferenceType.documentType, 
	DocumentReferenceType.xPath-list.xPath, 
	DocumentReferenceType.languageID, DocumentReferenceType.localeCode, 
	DocumentReferenceType.versionID, 
	DocumentReferenceType.documentStatusCode, 
	DocumentReferenceType.documentDescription-list.documentDescription, 
	DutyType.amount, DutyType.duty, DutyType.dutyCode, 
	EconomicOperatorShortListType.limitationDescription-list.limitationDescription,
	EconomicOperatorShortListType.expectedQuantity, 
	EconomicOperatorShortListType.maximumQuantity, 
	EconomicOperatorShortListType.minimumQuantity, 
	EndorsementType.documentID, EndorsementType.approvalStatus, 
	EndorsementType.remarks-list.remarks, EndorserPartyType.roleCode, 
	EndorserPartyType.sequenceNumeric, 
	EnergyTaxReportType.taxEnergyAmount, 
	EnergyTaxReportType.taxEnergyOnAccountAmount, 
	EnergyTaxReportType.taxEnergyBalanceAmount, 
	EnvironmentalEmissionType.environmentalEmissionTypeCode, 
	EnvironmentalEmissionType.valueMeasure, 
	EnvironmentalEmissionType.description-list.description, 
	EvaluationCriteriaType.evaluationCriteriaTypeCode, 
	EvaluationCriteriaType.description-list.description, 
	EvaluationCriteriaType.thresholdAmount, 
	EvaluationCriteriaType.thresholdQuantity, 
	EvaluationCriteriaType.expressionCode-list.expressionCode, 
	EventType.identificationID, EventType.occurrenceDate, 
	EventType.occurrenceTime, EventType.typeCode, 
	EventType.description-list.description, EventType.completionIndicator,
	EventCommentType.comment, EventCommentType.issueDate, 
	EventCommentType.issueTime, EventLineItemType.lineNumberNumeric, 
	EventTacticType.comment, EventTacticType.quantity, 
	EventTacticEnumerationType.consumerIncentiveTacticTypeCode, 
	EventTacticEnumerationType.displayTacticTypeCode, 
	EventTacticEnumerationType.featureTacticTypeCode, 
	EventTacticEnumerationType.tradeItemPackingLabelingTypeCode, 
	EvidenceType.iD, EvidenceType.evidenceTypeCode, 
	EvidenceType.name-list.name, ExceptionCriteriaLineType.iD, 
	ExceptionCriteriaLineType.note-list.note, 
	ExceptionCriteriaLineType.thresholdValueComparisonCode, 
	ExceptionCriteriaLineType.thresholdQuantity, 
	ExceptionCriteriaLineType.exceptionStatusCode, 
	ExceptionCriteriaLineType.collaborationPriorityCode, 
	ExceptionCriteriaLineType.exceptionResolutionCode-list.exceptionResolutionCode,
	ExceptionCriteriaLineType.supplyChainActivityTypeCode, 
	ExceptionCriteriaLineType.performanceMetricTypeCode, 
	ExceptionNotificationLineType.iD, 
	ExceptionNotificationLineType.note-list.note, 
	ExceptionNotificationLineType.description, 
	ExceptionNotificationLineType.exceptionStatusCode, 
	ExceptionNotificationLineType.collaborationPriorityCode, 
	ExceptionNotificationLineType.resolutionCode, 
	ExceptionNotificationLineType.comparedValueMeasure, 
	ExceptionNotificationLineType.sourceValueMeasure, 
	ExceptionNotificationLineType.varianceQuantity, 
	ExceptionNotificationLineType.supplyChainActivityTypeCode, 
	ExceptionNotificationLineType.performanceMetricTypeCode, 
	ExchangeRateType.sourceCurrencyCode, 
	ExchangeRateType.sourceCurrencyBaseRate, 
	ExchangeRateType.targetCurrencyCode, 
	ExchangeRateType.targetCurrencyBaseRate, 
	ExchangeRateType.exchangeMarketID, ExchangeRateType.calculationRate, 
	ExchangeRateType.mathematicOperatorCode, ExchangeRateType.date, 
	ExternalReferenceType.uRI, ExternalReferenceType.documentHash, 
	ExternalReferenceType.hashAlgorithmMethod-list.hashAlgorithmMethod, 
	ExternalReferenceType.expiryDate, ExternalReferenceType.expiryTime, 
	ExternalReferenceType.mimeCode, ExternalReferenceType.formatCode, 
	ExternalReferenceType.encodingCode, 
	ExternalReferenceType.characterSetCode, 
	ExternalReferenceType.fileName, 
	ExternalReferenceType.description-list.description, 
	FinancialAccountType.iD, FinancialAccountType.name, 
	FinancialAccountType.aliasName, FinancialAccountType.accountTypeCode, 
	FinancialAccountType.accountFormatCode, 
	FinancialAccountType.currencyCode, 
	FinancialAccountType.paymentNote-list.paymentNote, 
	FinancialGuaranteeType.guaranteeTypeCode, 
	FinancialGuaranteeType.description-list.description, 
	FinancialGuaranteeType.liabilityAmount, 
	FinancialGuaranteeType.amountRate, FinancialInstitutionType.iD, 
	FinancialInstitutionType.name, 
	ForecastExceptionType.forecastPurposeCode, 
	ForecastExceptionType.forecastTypeCode, 
	ForecastExceptionType.issueDate, ForecastExceptionType.issueTime, 
	ForecastExceptionType.dataSourceCode, 
	ForecastExceptionType.comparisonDataCode, 
	ForecastExceptionType.comparisonForecastIssueTime, 
	ForecastExceptionType.comparisonForecastIssueDate, 
	ForecastExceptionCriteriaLineType.forecastPurposeCode, 
	ForecastExceptionCriteriaLineType.forecastTypeCode, 
	ForecastExceptionCriteriaLineType.comparisonDataSourceCode, 
	ForecastExceptionCriteriaLineType.dataSourceCode, 
	ForecastExceptionCriteriaLineType.timeDeltaDaysQuantity, 
	ForecastLineType.iD, ForecastLineType.note-list.note, 
	ForecastLineType.frozenDocumentIndicator, 
	ForecastLineType.forecastTypeCode, ForecastRevisionLineType.iD, 
	ForecastRevisionLineType.note-list.note, 
	ForecastRevisionLineType.description, 
	ForecastRevisionLineType.revisedForecastLineID, 
	ForecastRevisionLineType.sourceForecastIssueDate, 
	ForecastRevisionLineType.sourceForecastIssueTime, 
	ForecastRevisionLineType.adjustmentReasonCode, 
	FrameworkAgreementType.expectedOperatorQuantity, 
	FrameworkAgreementType.maximumOperatorQuantity, 
	FrameworkAgreementType.justification-list.justification, 
	FrameworkAgreementType.frequency-list.frequency, GoodsItemType.iD, 
	GoodsItemType.sequenceNumberID, 
	GoodsItemType.description-list.description, 
	GoodsItemType.hazardousRiskIndicator, 
	GoodsItemType.declaredCustomsValueAmount, 
	GoodsItemType.declaredForCarriageValueAmount, 
	GoodsItemType.declaredStatisticsValueAmount, 
	GoodsItemType.freeOnBoardValueAmount, 
	GoodsItemType.insuranceValueAmount, GoodsItemType.valueAmount, 
	GoodsItemType.grossWeightMeasure, GoodsItemType.netWeightMeasure, 
	GoodsItemType.netNetWeightMeasure, 
	GoodsItemType.chargeableWeightMeasure, 
	GoodsItemType.grossVolumeMeasure, GoodsItemType.netVolumeMeasure, 
	GoodsItemType.quantity, GoodsItemType.preferenceCriterionCode, 
	GoodsItemType.requiredCustomsID, GoodsItemType.customsStatusCode, 
	GoodsItemType.customsTariffQuantity, 
	GoodsItemType.customsImportClassifiedIndicator, 
	GoodsItemType.chargeableQuantity, GoodsItemType.returnableQuantity, 
	GoodsItemContainerType.iD, GoodsItemContainerType.quantity, 
	HazardousGoodsTransitType.transportEmergencyCardCode, 
	HazardousGoodsTransitType.packingCriteriaCode, 
	HazardousGoodsTransitType.hazardousRegulationCode, 
	HazardousGoodsTransitType.inhalationToxicityZoneCode, 
	HazardousGoodsTransitType.transportAuthorizationCode, 
	HazardousItemType.iD, HazardousItemType.placardNotation, 
	HazardousItemType.placardEndorsement, 
	HazardousItemType.additionalInformation, HazardousItemType.uNDGCode, 
	HazardousItemType.emergencyProceduresCode, 
	HazardousItemType.medicalFirstAidGuideCode, 
	HazardousItemType.technicalName, HazardousItemType.categoryName, 
	HazardousItemType.hazardousCategoryCode, 
	HazardousItemType.upperOrangeHazardPlacardID, 
	HazardousItemType.lowerOrangeHazardPlacardID, 
	HazardousItemType.markingID, HazardousItemType.hazardClassID, 
	HazardousItemType.netWeightMeasure, 
	HazardousItemType.netVolumeMeasure, HazardousItemType.quantity, 
	ImmobilizedSecurityType.immobilizationCertificateID, 
	ImmobilizedSecurityType.securityID, ImmobilizedSecurityType.issueDate,
	ImmobilizedSecurityType.faceValueAmount, 
	ImmobilizedSecurityType.marketValueAmount, 
	ImmobilizedSecurityType.sharesNumberQuantity, 
	InstructionForReturnsLineType.iD, 
	InstructionForReturnsLineType.note-list.note, 
	InstructionForReturnsLineType.quantity, InventoryReportLineType.iD, 
	InventoryReportLineType.note-list.note, 
	InventoryReportLineType.quantity, 
	InventoryReportLineType.inventoryValueAmount, 
	InventoryReportLineType.availabilityDate, 
	InventoryReportLineType.availabilityStatusCode, InvoiceLineType.iD, 
	InvoiceLineType.uUID, InvoiceLineType.note-list.note, 
	InvoiceLineType.invoicedQuantity, InvoiceLineType.lineExtensionAmount,
	InvoiceLineType.taxPointDate, InvoiceLineType.accountingCostCode, 
	InvoiceLineType.accountingCost, InvoiceLineType.paymentPurposeCode, 
	InvoiceLineType.freeOfChargeIndicator, 
	ItemType.description-list.description, ItemType.packQuantity, 
	ItemType.packSizeNumeric, ItemType.catalogueIndicator, ItemType.name, 
	ItemType.hazardousRiskIndicator, ItemType.additionalInformation, 
	ItemType.keyword-list.keyword, ItemType.brandName-list.brandName, 
	ItemType.modelName-list.modelName, ItemComparisonType.priceAmount, 
	ItemComparisonType.quantity, ItemIdentificationType.iD, 
	ItemIdentificationType.extendedID, 
	ItemInformationRequestLineType.timeFrequencyCode, 
	ItemInformationRequestLineType.supplyChainActivityTypeCode, 
	ItemInformationRequestLineType.forecastTypeCode, 
	ItemInformationRequestLineType.performanceMetricTypeCode, 
	ItemInstanceType.productTraceID, ItemInstanceType.manufactureDate, 
	ItemInstanceType.manufactureTime, ItemInstanceType.bestBeforeDate, 
	ItemInstanceType.registrationID, ItemInstanceType.serialID, 
	ItemLocationQuantityType.leadTimeMeasure, 
	ItemLocationQuantityType.minimumQuantity, 
	ItemLocationQuantityType.maximumQuantity, 
	ItemLocationQuantityType.hazardousRiskIndicator, 
	ItemLocationQuantityType.tradingRestrictions-list.tradingRestrictions,
	ItemManagementProfileType.frozenPeriodDaysNumeric, 
	ItemManagementProfileType.minimumInventoryQuantity, 
	ItemManagementProfileType.multipleOrderQuantity, 
	ItemManagementProfileType.orderIntervalDaysNumeric, 
	ItemManagementProfileType.replenishmentOwnerDescription, 
	ItemManagementProfileType.targetServicePercent, 
	ItemManagementProfileType.targetInventoryQuantity, 
	ItemPropertyType.iD, ItemPropertyType.name, ItemPropertyType.nameCode,
	ItemPropertyType.testMethod, ItemPropertyType.value, 
	ItemPropertyType.valueQuantity, 
	ItemPropertyType.valueQualifier-list.valueQualifier, 
	ItemPropertyType.importanceCode, 
	ItemPropertyType.listValue-list.listValue, ItemPropertyGroupType.iD, 
	ItemPropertyGroupType.name, ItemPropertyGroupType.importanceCode, 
	ItemPropertyRangeType.minimumValue, 
	ItemPropertyRangeType.maximumValue, LanguageType.iD, 
	LanguageType.name, LanguageType.localeCode, LineItemType.iD, 
	LineItemType.salesOrderID, LineItemType.uUID, 
	LineItemType.note-list.note, LineItemType.lineStatusCode, 
	LineItemType.quantity, LineItemType.lineExtensionAmount, 
	LineItemType.totalTaxAmount, LineItemType.minimumQuantity, 
	LineItemType.maximumQuantity, LineItemType.minimumBackorderQuantity, 
	LineItemType.maximumBackorderQuantity, 
	LineItemType.inspectionMethodCode, 
	LineItemType.partialDeliveryIndicator, 
	LineItemType.backOrderAllowedIndicator, 
	LineItemType.accountingCostCode, LineItemType.accountingCost, 
	LineItemType.warrantyInformation-list.warrantyInformation, 
	LineReferenceType.lineID, LineReferenceType.uUID, 
	LineReferenceType.lineStatusCode, LocationType.iD, 
	LocationType.description, LocationType.conditions, 
	LocationType.countrySubentity, LocationType.countrySubentityCode, 
	LocationType.locationTypeCode, LocationType.informationURI, 
	LocationCoordinateType.coordinateSystemCode, 
	LocationCoordinateType.latitudeDegreesMeasure, 
	LocationCoordinateType.latitudeMinutesMeasure, 
	LocationCoordinateType.latitudeDirectionCode, 
	LocationCoordinateType.longitudeDegreesMeasure, 
	LocationCoordinateType.longitudeMinutesMeasure, 
	LocationCoordinateType.longitudeDirectionCode, 
	LocationCoordinateType.altitudeMeasure, 
	LotIdentificationType.lotNumberID, LotIdentificationType.expiryDate, 
	MaritimeTransportType.vesselID, MaritimeTransportType.vesselName, 
	MeterType.meterNumber, MeterType.meterName, MeterType.meterConstant, 
	MeterType.meterConstantCode, MeterType.totalDeliveredQuantity, 
	MeterPropertyType.name, MeterPropertyType.nameCode, 
	MeterPropertyType.value-list.value, MeterPropertyType.valueQuantity, 
	MeterPropertyType.valueQualifier-list.valueQualifier, 
	MeterReadingType.meterReadingType, 
	MeterReadingType.meterReadingTypeCode, 
	MeterReadingType.previousMeterReadingDate, 
	MeterReadingType.previousMeterQuantity, 
	MeterReadingType.latestMeterReadingDate, 
	MeterReadingType.latestMeterQuantity, 
	MeterReadingType.meterReadingMethod, 
	MeterReadingType.meterReadingMethodCode, 
	MeterReadingType.meterReadingComments-list.meterReadingComments, 
	MeterReadingType.deliveredQuantity, 
	MiscellaneousEventType.miscellaneousEventTypeCode, 
	MonetaryTotalType.lineExtensionAmount, 
	MonetaryTotalType.taxExclusiveAmount, 
	MonetaryTotalType.taxInclusiveAmount, 
	MonetaryTotalType.allowanceTotalAmount, 
	MonetaryTotalType.chargeTotalAmount, MonetaryTotalType.prepaidAmount, 
	MonetaryTotalType.payableRoundingAmount, 
	MonetaryTotalType.payableAmount, 
	MonetaryTotalType.payableAlternativeAmount, 
	NotificationRequirementType.notificationTypeCode, 
	OnAccountPaymentType.estimatedConsumedQuantity, 
	OnAccountPaymentType.note, OrderLineType.substitutionStatusCode, 
	OrderLineType.note-list.note, OrderLineReferenceType.lineID, 
	OrderLineReferenceType.salesOrderLineID, OrderLineReferenceType.uUID, 
	OrderLineReferenceType.lineStatusCode, OrderReferenceType.iD, 
	OrderReferenceType.salesOrderID, OrderReferenceType.copyIndicator, 
	OrderReferenceType.uUID, OrderReferenceType.issueDate, 
	OrderReferenceType.issueTime, OrderReferenceType.customerReference, 
	OrderReferenceType.orderTypeCode, PackageType.iD, 
	PackageType.quantity, PackageType.returnableMaterialIndicator, 
	PackageType.packageLevelCode, PackageType.packagingTypeCode, 
	PackageType.packingMaterial-list.packingMaterial, PackageType.traceID,
	PartyType.markCareIndicator, PartyType.markAttentionIndicator, 
	PartyType.websiteURI, PartyType.logoReferenceID, PartyType.endpointID,
	PartyType.industryClassificationCode, PartyIdentificationType.iD, 
	PartyLegalEntityType.registrationName, PartyLegalEntityType.companyID,
	PartyLegalEntityType.registrationDate, 
	PartyLegalEntityType.registrationExpirationDate, 
	PartyLegalEntityType.companyLegalFormCode, 
	PartyLegalEntityType.soleProprietorshipIndicator, 
	PartyLegalEntityType.companyLiquidationStatusCode, 
	PartyLegalEntityType.corporateStockAmount, 
	PartyLegalEntityType.fullyPaidSharesIndicator, PartyNameType.name, 
	PartyTaxSchemeType.registrationName, PartyTaxSchemeType.companyID, 
	PartyTaxSchemeType.taxLevelCode, 
	PartyTaxSchemeType.exemptionReasonCode, 
	PartyTaxSchemeType.exemptionReason, PaymentType.iD, 
	PaymentType.paidAmount, PaymentType.receivedDate, 
	PaymentType.paidDate, PaymentType.paidTime, PaymentType.instructionID,
	PaymentMandateType.iD, PaymentMandateType.mandateTypeCode, 
	PaymentMandateType.clause-list.clause, 
	PaymentMandateType.clauseCode-list.clauseCode, 
	PaymentMandateType.maximumPaymentInstructionsNumeric, 
	PaymentMandateType.maximumPaidAmount, PaymentMandateType.signatureID, 
	PaymentMeansType.iD, PaymentMeansType.paymentMeansCode, 
	PaymentMeansType.paymentDueDate, PaymentMeansType.paymentChannelCode, 
	PaymentMeansType.instructionID, 
	PaymentMeansType.instructionNote-list.instructionNote, 
	PaymentMeansType.paymentID-list.paymentID, PaymentTermsType.iD, 
	PaymentTermsType.paymentMeansID-list.paymentMeansID, 
	PaymentTermsType.prepaidPaymentReferenceID, 
	PaymentTermsType.note-list.note, PaymentTermsType.referenceEventCode, 
	PaymentTermsType.settlementDiscountPercent, 
	PaymentTermsType.penaltySurchargePercent, 
	PaymentTermsType.paymentPercent, PaymentTermsType.amount, 
	PaymentTermsType.settlementDiscountAmount, 
	PaymentTermsType.penaltyAmount, 
	PaymentTermsType.paymentTermsDetailsURI, 
	PaymentTermsType.paymentDueDate, PaymentTermsType.installmentDueDate, 
	PaymentTermsType.invoicingPartyReference, PerformanceDataLineType.iD, 
	PerformanceDataLineType.note-list.note, 
	PerformanceDataLineType.performanceValueQuantity, 
	PerformanceDataLineType.performanceMetricTypeCode, 
	PeriodType.startDate, PeriodType.startTime, PeriodType.endDate, 
	PeriodType.endTime, PeriodType.durationMeasure, 
	PeriodType.descriptionCode-list.descriptionCode, 
	PeriodType.description-list.description, PersonType.iD, 
	PersonType.firstName, PersonType.familyName, PersonType.title, 
	PersonType.middleName, PersonType.nameSuffix, PersonType.jobTitle, 
	PersonType.nationalityID, PersonType.genderCode, PersonType.birthDate,
	PersonType.organizationDepartment, PhysicalAttributeType.attributeID, 
	PhysicalAttributeType.positionCode, 
	PhysicalAttributeType.descriptionCode, 
	PhysicalAttributeType.description-list.description, PickupType.iD, 
	PickupType.actualPickupDate, PickupType.actualPickupTime, 
	PickupType.earliestPickupDate, PickupType.earliestPickupTime, 
	PickupType.latestPickupDate, PickupType.latestPickupTime, 
	PowerOfAttorneyType.iD, PowerOfAttorneyType.issueDate, 
	PowerOfAttorneyType.issueTime, 
	PowerOfAttorneyType.description-list.description, 
	PriceType.priceAmount, PriceType.baseQuantity, 
	PriceType.priceChangeReason-list.priceChangeReason, 
	PriceType.priceTypeCode, PriceType.priceType, 
	PriceType.orderableUnitFactorRate, PriceListType.iD, 
	PriceListType.statusCode, 
	ProcessJustificationType.previousCancellationReasonCode, 
	ProcessJustificationType.processReasonCode, 
	ProcessJustificationType.processReason-list.processReason, 
	ProcessJustificationType.description-list.description, 
	ProcurementProjectType.iD, ProcurementProjectType.name-list.name, 
	ProcurementProjectType.description-list.description, 
	ProcurementProjectType.procurementTypeCode, 
	ProcurementProjectType.procurementSubTypeCode, 
	ProcurementProjectType.qualityControlCode, 
	ProcurementProjectType.requiredFeeAmount, 
	ProcurementProjectType.feeDescription-list.feeDescription, 
	ProcurementProjectType.requestedDeliveryDate, 
	ProcurementProjectType.estimatedOverallContractQuantity, 
	ProcurementProjectLotType.iD, 
	PromotionalEventType.promotionalEventTypeCode, 
	PromotionalEventType.submissionDate, 
	PromotionalEventType.firstShipmentAvailibilityDate, 
	PromotionalEventType.latestProposalAcceptanceDate, 
	PromotionalEventLineItemType.amount, 
	PromotionalSpecificationType.specificationID, 
	QualificationResolutionType.admissionCode, 
	QualificationResolutionType.procurementProjectLotID, 
	QualificationResolutionType.exclusionReason-list.exclusionReason, 
	QualificationResolutionType.resolution-list.resolution, 
	QualificationResolutionType.resolutionDate, 
	QualificationResolutionType.resolutionTime, 
	QualifyingPartyType.participationPercent, 
	QualifyingPartyType.personalSituation-list.personalSituation, 
	QualifyingPartyType.operatingYearsQuantity, 
	QualifyingPartyType.employeeQuantity, 
	QualifyingPartyType.businessClassificationEvidenceID, 
	QualifyingPartyType.businessIdentityEvidenceID, QuotationLineType.iD, 
	QuotationLineType.note-list.note, QuotationLineType.quantity, 
	QuotationLineType.lineExtensionAmount, 
	QuotationLineType.totalTaxAmount, 
	QuotationLineType.requestForQuotationLineID, 
	RailTransportType.trainID, RailTransportType.railCarID, 
	ReceiptLineType.iD, ReceiptLineType.uUID, 
	ReceiptLineType.note-list.note, ReceiptLineType.receivedQuantity, 
	ReceiptLineType.shortQuantity, ReceiptLineType.shortageActionCode, 
	ReceiptLineType.rejectedQuantity, ReceiptLineType.rejectReasonCode, 
	ReceiptLineType.rejectReason, ReceiptLineType.rejectActionCode, 
	ReceiptLineType.quantityDiscrepancyCode, 
	ReceiptLineType.oversupplyQuantity, ReceiptLineType.receivedDate, 
	ReceiptLineType.timingComplaintCode, ReceiptLineType.timingComplaint, 
	RegulationType.name-list.name, RegulationType.legalReference, 
	RegulationType.ontologyURI, RelatedItemType.iD, 
	RelatedItemType.quantity, 
	RelatedItemType.description-list.description, ReminderLineType.iD, 
	ReminderLineType.note-list.note, ReminderLineType.uUID, 
	ReminderLineType.balanceBroughtForwardIndicator, 
	ReminderLineType.debitLineAmount, ReminderLineType.creditLineAmount, 
	ReminderLineType.accountingCostCode, ReminderLineType.accountingCost, 
	ReminderLineType.penaltySurchargePercent, ReminderLineType.amount, 
	ReminderLineType.paymentPurposeCode, RemittanceAdviceLineType.iD, 
	RemittanceAdviceLineType.note-list.note, 
	RemittanceAdviceLineType.uUID, 
	RemittanceAdviceLineType.debitLineAmount, 
	RemittanceAdviceLineType.creditLineAmount, 
	RemittanceAdviceLineType.balanceAmount, 
	RemittanceAdviceLineType.paymentPurposeCode, 
	RemittanceAdviceLineType.invoicingPartyReference, RenewalType.amount, 
	RequestForQuotationLineType.iD, RequestForQuotationLineType.uUID, 
	RequestForQuotationLineType.note-list.note, 
	RequestForQuotationLineType.optionalLineItemIndicator, 
	RequestForQuotationLineType.privacyCode, 
	RequestForQuotationLineType.securityClassificationCode, 
	RequestForTenderLineType.iD, RequestForTenderLineType.uUID, 
	RequestForTenderLineType.note-list.note, 
	RequestForTenderLineType.quantity, 
	RequestForTenderLineType.minimumQuantity, 
	RequestForTenderLineType.maximumQuantity, 
	RequestForTenderLineType.maximumTaxExclusiveAmount, 
	RequestForTenderLineType.maximumTaxInclusiveAmount, 
	ResponseType.referenceID, ResponseType.responseCode, 
	ResponseType.description-list.description, ResponseType.effectiveDate,
	ResponseType.effectiveTime, ResultOfVerificationType.validatorID, 
	ResultOfVerificationType.validationResultCode, 
	ResultOfVerificationType.validationDate, 
	ResultOfVerificationType.validationTime, 
	ResultOfVerificationType.validateProcess, 
	ResultOfVerificationType.validateTool, 
	ResultOfVerificationType.validateToolVersion, 
	RetailPlannedImpactType.amount, 
	RetailPlannedImpactType.forecastPurposeCode, 
	RetailPlannedImpactType.forecastTypeCode, 
	RoadTransportType.licensePlateID, SalesItemType.quantity, 
	SecondaryHazardType.iD, SecondaryHazardType.placardNotation, 
	SecondaryHazardType.placardEndorsement, 
	SecondaryHazardType.emergencyProceduresCode, 
	SecondaryHazardType.extension, ServicePointType.sequenceNumberID, 
	ServicePointType.transportModeCode, 
	ServicePointType.remarks-list.remarks, ServiceProviderPartyType.iD, 
	ServiceProviderPartyType.serviceTypeCode, 
	ServiceProviderPartyType.serviceType-list.serviceType, 
	ShareholderPartyType.partecipationPercent, ShipmentType.iD, 
	ShipmentType.shippingPriorityLevelCode, ShipmentType.handlingCode, 
	ShipmentType.handlingInstructions, ShipmentType.information, 
	ShipmentType.grossWeightMeasure, ShipmentType.netWeightMeasure, 
	ShipmentType.netNetWeightMeasure, ShipmentType.grossVolumeMeasure, 
	ShipmentType.netVolumeMeasure, ShipmentType.totalGoodsItemQuantity, 
	ShipmentType.totalTransportHandlingUnitQuantity, 
	ShipmentType.insuranceValueAmount, 
	ShipmentType.declaredCustomsValueAmount, 
	ShipmentType.declaredForCarriageValueAmount, 
	ShipmentType.declaredStatisticsValueAmount, 
	ShipmentType.freeOnBoardValueAmount, 
	ShipmentType.specialInstructions-list.specialInstructions, 
	ShipmentType.deliveryInstructions-list.deliveryInstructions, 
	ShipmentType.splitConsignmentIndicator, 
	ShipmentType.consignmentQuantity, ShipmentStageType.iD, 
	ShipmentStageType.transportModeCode, 
	ShipmentStageType.transportMeansTypeCode, 
	ShipmentStageType.transitDirectionCode, 
	ShipmentStageType.preCarriageIndicator, 
	ShipmentStageType.onCarriageIndicator, 
	ShipmentStageType.estimatedDeliveryDate, 
	ShipmentStageType.estimatedDeliveryTime, 
	ShipmentStageType.requiredDeliveryDate, 
	ShipmentStageType.requiredDeliveryTime, 
	ShipmentStageType.loadingSequenceID, 
	ShipmentStageType.successiveSequenceID, 
	ShipmentStageType.instructions, 
	ShipmentStageType.demurrageInstructions, SignatureType-1.iD, 
	SignatureType-1.note-list.note, SignatureType-1.validationDate, 
	SignatureType-1.validationTime, SignatureType-1.validatorID, 
	SignatureType-1.canonicalizationMethod, 
	SignatureType-1.signatureMethod, StatementLineType.iD, 
	StatementLineType.note-list.note, StatementLineType.uUID, 
	StatementLineType.balanceBroughtForwardIndicator, 
	StatementLineType.debitLineAmount, StatementLineType.creditLineAmount,
	StatementLineType.balanceAmount, StatementLineType.paymentPurposeCode,
	StatusType.conditionCode, StatusType.referenceDate, 
	StatusType.referenceTime, StatusType.description-list.description, 
	StatusType.statusReasonCode, 
	StatusType.statusReason-list.statusReason, StatusType.sequenceID, 
	StatusType.text-list.text, StatusType.indicationIndicator, 
	StatusType.percent, 
	StatusType.conditionValueMeasure-list.conditionValueMeasure, 
	StatusType.reliabilityPercent, StockAvailabilityReportLineType.iD, 
	StockAvailabilityReportLineType.note-list.note, 
	StockAvailabilityReportLineType.quantity, 
	StockAvailabilityReportLineType.valueAmount, 
	StockAvailabilityReportLineType.availabilityDate, 
	StockAvailabilityReportLineType.availabilityStatusCode, 
	StowageType.locationID, StowageType.location-list.location, 
	SubcontractTermsType.rate, SubcontractTermsType.unknownPriceIndicator,
	SubcontractTermsType.description-list.description, 
	SubcontractTermsType.amount, SubscriberConsumptionType.consumptionID, 
	SubscriberConsumptionType.specificationTypeCode, 
	SubscriberConsumptionType.note-list.note, 
	SubscriberConsumptionType.totalMeteredQuantity, 
	SupplierConsumptionType.description, 
	SupplierPartyType.customerAssignedAccountID, 
	SupplierPartyType.additionalAccountID-list.additionalAccountID, 
	SupplierPartyType.dataSendingCapability, TaxCategoryType.iD, 
	TaxCategoryType.name, TaxCategoryType.percent, 
	TaxCategoryType.baseUnitMeasure, TaxCategoryType.perUnitAmount, 
	TaxCategoryType.taxExemptionReasonCode, 
	TaxCategoryType.taxExemptionReason, TaxCategoryType.tierRange, 
	TaxCategoryType.tierRatePercent, TaxSchemeType.iD, TaxSchemeType.name,
	TaxSchemeType.taxTypeCode, TaxSchemeType.currencyCode, 
	TaxSubtotalType.taxableAmount, TaxSubtotalType.taxAmount, 
	TaxSubtotalType.calculationSequenceNumeric, 
	TaxSubtotalType.transactionCurrencyTaxAmount, TaxSubtotalType.percent,
	TaxSubtotalType.baseUnitMeasure, TaxSubtotalType.perUnitAmount, 
	TaxSubtotalType.tierRange, TaxSubtotalType.tierRatePercent, 
	TaxTotalType.taxAmount, TaxTotalType.roundingAmount, 
	TaxTotalType.taxEvidenceIndicator, TaxTotalType.taxIncludedIndicator, 
	TelecommunicationsServiceType.iD, 
	TelecommunicationsServiceType.callDate, 
	TelecommunicationsServiceType.callTime, 
	TelecommunicationsServiceType.serviceNumberCalled, 
	TelecommunicationsServiceType.telecommunicationsServiceCategory, 
	TelecommunicationsServiceType.telecommunicationsServiceCategoryCode, 
	TelecommunicationsServiceType.movieTitle, 
	TelecommunicationsServiceType.roamingPartnerName-list.roamingPartnerName,
	TelecommunicationsServiceType.payPerView, 
	TelecommunicationsServiceType.quantity, 
	TelecommunicationsServiceType.telecommunicationsServiceCall, 
	TelecommunicationsServiceType.telecommunicationsServiceCallCode, 
	TelecommunicationsServiceType.callBaseAmount, 
	TelecommunicationsServiceType.callExtensionAmount, 
	TelecommunicationsSupplyType.telecommunicationsSupplyType, 
	TelecommunicationsSupplyType.telecommunicationsSupplyTypeCode, 
	TelecommunicationsSupplyType.privacyCode, 
	TelecommunicationsSupplyType.description, 
	TelecommunicationsSupplyType.totalAmount, 
	TelecommunicationsSupplyLineType.iD, 
	TelecommunicationsSupplyLineType.phoneNumber, 
	TelecommunicationsSupplyLineType.description, 
	TelecommunicationsSupplyLineType.lineExtensionAmount, 
	TemperatureType.attributeID, TemperatureType.measure, 
	TemperatureType.description-list.description, TenderLineType.iD, 
	TenderLineType.note-list.note, TenderLineType.quantity, 
	TenderLineType.lineExtensionAmount, TenderLineType.totalTaxAmount, 
	TenderLineType.orderableUnit-list.orderableUnit, 
	TenderLineType.contentUnitQuantity, 
	TenderLineType.orderQuantityIncrementNumeric, 
	TenderLineType.minimumOrderQuantity, 
	TenderLineType.maximumOrderQuantity, 
	TenderLineType.warrantyInformation-list.warrantyInformation, 
	TenderLineType.packLevelCode, TenderPreparationType.tenderEnvelopeID, 
	TenderPreparationType.tenderEnvelopeTypeCode, 
	TenderPreparationType.description-list.description, 
	TenderPreparationType.openTenderID, 
	TenderPreparationType.procurementProjectLotID-list.procurementProjectLotID,
	TenderRequirementType.name-list.name, 
	TenderRequirementType.description-list.description, 
	TenderResultType.tenderResultCode, 
	TenderResultType.description-list.description, 
	TenderResultType.advertisementAmount, TenderResultType.awardDate, 
	TenderResultType.awardTime, TenderResultType.receivedTenderQuantity, 
	TenderResultType.lowerTenderAmount, 
	TenderResultType.higherTenderAmount, TenderResultType.startDate, 
	TenderedProjectType.procurementProjectLotID, 
	TenderedProjectType.variantID, TenderedProjectType.feeAmount, 
	TenderedProjectType.feeDescription-list.feeDescription, 
	TendererPartyQualificationType.interestedProcurementLotsID-list.interestedProcurementLotsID,
	TendererQualificationRequestType.legalForm-list.legalForm, 
	TendererQualificationRequestType.personalSituation-list.personalSituation,
	TendererQualificationRequestType.operatingYearsQuantity, 
	TendererQualificationRequestType.employeeQuantity, 
	TendererQualificationRequestType.description-list.description, 
	TendererRequirementType.name-list.name, 
	TendererRequirementType.tendererRequirementTypeCode, 
	TendererRequirementType.description-list.description, 
	TenderingProcessType.iD, 
	TenderingProcessType.originalContractingSystemID, 
	TenderingProcessType.description-list.description, 
	TenderingProcessType.negotiationDescription-list.negotiationDescription,
	TenderingProcessType.procedureCode, TenderingProcessType.urgencyCode, 
	TenderingProcessType.expenseCode, 
	TenderingProcessType.partPresentationCode, 
	TenderingProcessType.contractingSystemCode, 
	TenderingProcessType.submissionMethodCode, 
	TenderingProcessType.candidateReductionConstraintIndicator, 
	TenderingProcessType.governmentAgreementConstraintIndicator, 
	TenderingTermsType.awardingMethodTypeCode, 
	TenderingTermsType.priceEvaluationCode, 
	TenderingTermsType.maximumVariantQuantity, 
	TenderingTermsType.variantConstraintIndicator, 
	TenderingTermsType.acceptedVariantsDescription-list.acceptedVariantsDescription,
	TenderingTermsType.priceRevisionFormulaDescription-list.priceRevisionFormulaDescription,
	TenderingTermsType.fundingProgramCode, 
	TenderingTermsType.fundingProgram-list.fundingProgram, 
	TenderingTermsType.maximumAdvertisementAmount, 
	TenderingTermsType.note-list.note, 
	TenderingTermsType.paymentFrequencyCode, 
	TenderingTermsType.economicOperatorRegistryURI, 
	TenderingTermsType.penaltyClauses-list.penaltyClauses, 
	TenderingTermsType.requiredCurriculaIndicator, TradeFinancingType.iD, 
	TradeFinancingType.financingInstrumentCode, 
	TradeFinancingType.clauseCode-list.clauseCode, 
	TradeFinancingType.clause-list.clause, 
	TradingTermsType.information-list.information, 
	TradingTermsType.reference, TransactionConditionsType.iD, 
	TransactionConditionsType.actionCode, 
	TransactionConditionsType.description-list.description, 
	TransportEquipmentType.iD, 
	TransportEquipmentType.referencedConsignmentID, 
	TransportEquipmentType.transportEquipmentTypeCode, 
	TransportEquipmentType.providerTypeCode, 
	TransportEquipmentType.ownerTypeCode, 
	TransportEquipmentType.sizeTypeCode, 
	TransportEquipmentType.dispositionCode, 
	TransportEquipmentType.fullnessIndicationCode, 
	TransportEquipmentType.refrigerationOnIndicator, 
	TransportEquipmentType.information, 
	TransportEquipmentType.returnabilityIndicator, 
	TransportEquipmentType.legalStatusIndicator, 
	TransportEquipmentType.airFlowPercent, 
	TransportEquipmentType.humidityPercent, 
	TransportEquipmentType.animalFoodApprovedIndicator, 
	TransportEquipmentType.humanFoodApprovedIndicator, 
	TransportEquipmentType.dangerousGoodsApprovedIndicator, 
	TransportEquipmentType.refrigeratedIndicator, 
	TransportEquipmentType.characteristics, 
	TransportEquipmentType.damageRemarks, 
	TransportEquipmentType.description, 
	TransportEquipmentType.specialTransportRequirments, 
	TransportEquipmentType.grossWeightMeasure, 
	TransportEquipmentType.grossVolumeMeasure, 
	TransportEquipmentType.tareWeightMeasure, 
	TransportEquipmentType.trackingDeviceCode, 
	TransportEquipmentType.powerIndicator, TransportEquipmentType.traceID,
	TransportEquipmentSealType.iD, 
	TransportEquipmentSealType.sealIssuerTypeCode, 
	TransportEquipmentSealType.condition, 
	TransportEquipmentSealType.sealStatusCode, 
	TransportEquipmentSealType.sealingPartyType, 
	TransportEventType.identificationID, 
	TransportEventType.occurrenceDate, TransportEventType.occurrenceTime, 
	TransportEventType.transportEventTypeCode, 
	TransportEventType.description, 
	TransportEventType.completionIndicator, 
	TransportExecutionTermsType.transportUserSpecialTerms-list.transportUserSpecialTerms,
	TransportExecutionTermsType.transportServiceProviderSpecialTerms-list.transportServiceProviderSpecialTerms,
	TransportExecutionTermsType.changeConditions-list.changeConditions, 
	TransportHandlingUnitType.iD, 
	TransportHandlingUnitType.transportHandlingUnitTypeCode, 
	TransportHandlingUnitType.handlingCode, 
	TransportHandlingUnitType.handlingInstructions, 
	TransportHandlingUnitType.hazardousRiskIndicator, 
	TransportHandlingUnitType.totalGoodsItemQuantity, 
	TransportHandlingUnitType.totalPackageQuantity, 
	TransportHandlingUnitType.damageRemarks-list.damageRemarks, 
	TransportHandlingUnitType.shippingMarks-list.shippingMarks, 
	TransportMeansType.journeyID, 
	TransportMeansType.registrationNationalityID, 
	TransportMeansType.registrationNationality-list.registrationNationality,
	TransportMeansType.directionCode, 
	TransportMeansType.transportMeansTypeCode, 
	TransportMeansType.tradeServiceCode, 
	TransportScheduleType.sequenceNumberID, 
	TransportScheduleType.referenceDate, 
	TransportScheduleType.referenceTime, 
	TransportScheduleType.reliabilityPercent, 
	TransportScheduleType.remarks-list.remarks, 
	TransportStatusType.timeDeviationIndicator, 
	TransportStatusType.conditionDeviationIndicator, 
	TransportationSegmentType.sequenceNumberID, 
	TransportationSegmentType.transportExecutionPlanReferenceID, 
	TransportationSegmentType.transportModeCode, 
	TransportationSegmentType.transportMeansTypeCode, 
	TransportationServiceType.transportServiceCode, 
	TransportationServiceType.tariffClassCode, 
	TransportationServiceType.priority, 
	TransportationServiceType.freightRateClassCode, 
	TransportationServiceType.transportationServiceDescription, 
	TransportationServiceType.transportationServiceDetailsURI, 
	TransportationServiceType.nominationDate, 
	TransportationServiceType.nominationTime, 
	UnstructuredPriceType.priceAmount, UnstructuredPriceType.timeAmount, 
	UtilityItemType.iD, UtilityItemType.subscriberID, 
	UtilityItemType.subscriberIDType, 
	UtilityItemType.subscriberIDTypeCode, 
	UtilityItemType.description-list.description, 
	UtilityItemType.packQuantity, UtilityItemType.packSizeNumeric, 
	UtilityItemType.consumptionType, UtilityItemType.consumptionTypeCode, 
	UtilityItemType.currentChargeType, 
	UtilityItemType.currentChargeTypeCode, 
	UtilityItemType.oneTimeChargeType, 
	UtilityItemType.oneTimeChargeTypeCode, WebSiteAccessType.uRI, 
	WebSiteAccessType.password, WebSiteAccessType.login
	AS "urn:oasis:names:specification:ubl:schema:xsd:CommonBasicComponents-2"
	    PREFIX "cbc"
    NAME Language-1 AS "Language"
    NAME Signature-1 AS "Signature"
    NAME ActivityDataLineType.iD, 
	ActivityDataLineType.supplyChainActivityTypeCode, 
	ActivityDataLineType.buyerCustomerParty, 
	ActivityDataLineType.sellerSupplierParty, 
	ActivityDataLineType.activityPeriod, 
	ActivityDataLineType.activityOriginLocation, 
	ActivityDataLineType.activityFinalLocation, 
	ActivityDataLineType.salesItem-list.salesItem, 
	ActivityPropertyType.name, ActivityPropertyType.value, AddressType.iD,
	AddressType.addressTypeCode, AddressType.addressFormatCode, 
	AddressType.postbox, AddressType.floor, AddressType.room, 
	AddressType.streetName, AddressType.additionalStreetName, 
	AddressType.blockName, AddressType.buildingName, 
	AddressType.buildingNumber, AddressType.inhouseMail, 
	AddressType.department, AddressType.markAttention, 
	AddressType.markCare, AddressType.plotIdentification, 
	AddressType.citySubdivisionName, AddressType.cityName, 
	AddressType.postalZone, AddressType.countrySubentity, 
	AddressType.countrySubentityCode, AddressType.region, 
	AddressType.district, AddressType.timezoneOffset, 
	AddressType.addressLine-list.addressLine, AddressType.country, 
	AddressType.locationCoordinate-list.locationCoordinate, 
	AddressLineType.line, AirTransportType.aircraftID, 
	AllowanceChargeType.iD, AllowanceChargeType.chargeIndicator, 
	AllowanceChargeType.allowanceChargeReasonCode, 
	AllowanceChargeType.allowanceChargeReason, 
	AllowanceChargeType.multiplierFactorNumeric, 
	AllowanceChargeType.prepaidIndicator, 
	AllowanceChargeType.sequenceNumeric, AllowanceChargeType.amount, 
	AllowanceChargeType.baseAmount, 
	AllowanceChargeType.accountingCostCode, 
	AllowanceChargeType.accountingCost, AllowanceChargeType.perUnitAmount,
	AllowanceChargeType.taxCategory-list.taxCategory, 
	AllowanceChargeType.taxTotal, 
	AllowanceChargeType.paymentMeans-list.paymentMeans, 
	AppealTermsType.description-list.description, 
	AppealTermsType.presentationPeriod, 
	AppealTermsType.appealInformationParty, 
	AppealTermsType.appealReceiverParty, AppealTermsType.mediationParty, 
	AttachmentType.embeddedDocumentBinaryObject, 
	AttachmentType.externalReference, 
	AuctionTermsType.auctionConstraintIndicator, 
	AuctionTermsType.justificationDescription-list.justificationDescription,
	AuctionTermsType.description-list.description, 
	AuctionTermsType.processDescription-list.processDescription, 
	AuctionTermsType.conditionsDescription-list.conditionsDescription, 
	AuctionTermsType.electronicDeviceDescription-list.electronicDeviceDescription,
	AuctionTermsType.auctionURI, AwardingCriteriaType.iD, 
	AwardingCriteriaType.awardingCriteriaTypeCode, 
	AwardingCriteriaType.description-list.description, 
	AwardingCriteriaType.weightNumeric, 
	AwardingCriteriaType.weight-list.weight, 
	AwardingCriteriaType.calculationExpression-list.calculationExpression,
	AwardingCriteriaType.calculationExpressionCode, 
	AwardingCriteriaType.minimumQuantity, 
	AwardingCriteriaType.maximumQuantity, 
	AwardingCriteriaType.minimumAmount, 
	AwardingCriteriaType.maximumAmount, 
	AwardingCriteriaType.minimumImprovementBid-list.minimumImprovementBid,
	AwardingCriteriaType.subordinateAwardingCriteria-list.subordinateAwardingCriteria,
	AwardingCriteriaResponseType.iD, 
	AwardingCriteriaResponseType.awardingCriteriaID, 
	AwardingCriteriaResponseType.awardingCriteriaDescription-list.awardingCriteriaDescription,
	AwardingCriteriaResponseType.description-list.description, 
	AwardingCriteriaResponseType.quantity, 
	AwardingCriteriaResponseType.amount, 
	AwardingCriteriaResponseType.subordinateAwardingCriteriaResponse-list.subordinateAwardingCriteriaResponse,
	AwardingTermsType.weightingAlgorithmCode, 
	AwardingTermsType.description-list.description, 
	AwardingTermsType.technicalCommitteeDescription-list.technicalCommitteeDescription,
	AwardingTermsType.lowTendersDescription-list.lowTendersDescription, 
	AwardingTermsType.awardingCriteria-list.awardingCriteria, 
	AwardingTermsType.technicalCommitteePerson-list.technicalCommitteePerson,
	BillingReferenceType.invoiceDocumentReference, 
	BillingReferenceType.selfBilledInvoiceDocumentReference, 
	BillingReferenceType.creditNoteDocumentReference, 
	BillingReferenceType.selfBilledCreditNoteDocumentReference, 
	BillingReferenceType.debitNoteDocumentReference, 
	BillingReferenceType.reminderDocumentReference, 
	BillingReferenceType.additionalDocumentReference, 
	BillingReferenceType.billingReferenceLine-list.billingReferenceLine, 
	BillingReferenceLineType.iD, BillingReferenceLineType.amount, 
	BillingReferenceLineType.allowanceCharge-list.allowanceCharge, 
	BranchType.iD, BranchType.name, BranchType.financialInstitution, 
	BranchType.address, BudgetAccountType.iD, 
	BudgetAccountType.budgetYearNumeric, 
	BudgetAccountType.requiredClassificationScheme, 
	BudgetAccountLineType.iD, BudgetAccountLineType.totalAmount, 
	BudgetAccountLineType.budgetAccount-list.budgetAccount, 
	BudgetAmountType.estimatedOverallContractAmount, 
	BudgetAmountType.totalAmount, BudgetAmountType.taxExclusiveAmount, 
	BudgetAmountType.minimumAmount, 
	BudgetAmountType.monetaryScope-list.monetaryScope, 
	BudgetAmountType.averageSubsequentContractAmount, 
	BudgetAmountType.applicableTaxCategory-list.applicableTaxCategory, 
	CapabilityType.capabilityTypeCode, 
	CapabilityType.description-list.description, 
	CapabilityType.valueAmount, CapabilityType.valueQuantity, 
	CapabilityType.evidenceSuppliedID-list.evidenceSuppliedID, 
	CapabilityType.validityPeriod, CardAccountType.primaryAccountNumberID,
	CardAccountType.networkID, CardAccountType.cardTypeCode, 
	CardAccountType.validityStartDate, CardAccountType.expiryDate, 
	CardAccountType.issuerID, CardAccountType.issueNumberID, 
	CardAccountType.cV2ID, CardAccountType.cardChipCode, 
	CardAccountType.chipApplicationID, CardAccountType.holderName, 
	CatalogueItemSpecificationUpdateLineType.iD, 
	CatalogueItemSpecificationUpdateLineType.contractorCustomerParty, 
	CatalogueItemSpecificationUpdateLineType.sellerSupplierParty, 
	CatalogueItemSpecificationUpdateLineType.item, CatalogueLineType.iD, 
	CatalogueLineType.actionCode, CatalogueLineType.lifeCycleStatusCode, 
	CatalogueLineType.contractSubdivision, 
	CatalogueLineType.note-list.note, 
	CatalogueLineType.orderableIndicator, CatalogueLineType.orderableUnit,
	CatalogueLineType.contentUnitQuantity, 
	CatalogueLineType.orderQuantityIncrementNumeric, 
	CatalogueLineType.minimumOrderQuantity, 
	CatalogueLineType.maximumOrderQuantity, 
	CatalogueLineType.warrantyInformation-list.warrantyInformation, 
	CatalogueLineType.packLevelCode, 
	CatalogueLineType.contractorCustomerParty, 
	CatalogueLineType.sellerSupplierParty, 
	CatalogueLineType.warrantyParty, 
	CatalogueLineType.warrantyValidityPeriod, 
	CatalogueLineType.lineValidityPeriod, 
	CatalogueLineType.itemComparison-list.itemComparison, 
	CatalogueLineType.componentRelatedItem-list.componentRelatedItem, 
	CatalogueLineType.accessoryRelatedItem-list.accessoryRelatedItem, 
	CatalogueLineType.requiredRelatedItem-list.requiredRelatedItem, 
	CatalogueLineType.replacementRelatedItem-list.replacementRelatedItem, 
	CatalogueLineType.complementaryRelatedItem-list.complementaryRelatedItem,
	CatalogueLineType.requiredItemLocationQuantity-list.requiredItemLocationQuantity,
	CatalogueLineType.documentReference-list.documentReference, 
	CatalogueLineType.item, 
	CatalogueLineType.keywordItemProperty-list.keywordItemProperty, 
	CataloguePricingUpdateLineType.iD, 
	CataloguePricingUpdateLineType.contractorCustomerParty, 
	CataloguePricingUpdateLineType.sellerSupplierParty, 
	CataloguePricingUpdateLineType.requiredItemLocationQuantity-list.requiredItemLocationQuantity,
	CatalogueReferenceType.iD, CatalogueReferenceType.uUID, 
	CatalogueReferenceType.issueDate, CatalogueReferenceType.issueTime, 
	CatalogueReferenceType.revisionDate, 
	CatalogueReferenceType.revisionTime, 
	CatalogueReferenceType.note-list.note, 
	CatalogueReferenceType.description-list.description, 
	CatalogueReferenceType.versionID, 
	CatalogueReferenceType.previousVersionID, CatalogueRequestLineType.iD,
	CatalogueRequestLineType.contractSubdivision, 
	CatalogueRequestLineType.note-list.note, 
	CatalogueRequestLineType.lineValidityPeriod, 
	CatalogueRequestLineType.requiredItemLocationQuantity-list.requiredItemLocationQuantity,
	CatalogueRequestLineType.item, CertificateType.iD, 
	CertificateType.certificateTypeCode, CertificateType.certificateType, 
	CertificateType.remarks, CertificateType.issuerParty, 
	CertificateType.documentReference-list.documentReference, 
	CertificateType.signature-list.signature, 
	CertificateOfOriginApplicationType.referenceID, 
	CertificateOfOriginApplicationType.certificateType, 
	CertificateOfOriginApplicationType.applicationStatusCode, 
	CertificateOfOriginApplicationType.originalJobID, 
	CertificateOfOriginApplicationType.previousJobID, 
	CertificateOfOriginApplicationType.remarks, 
	CertificateOfOriginApplicationType.shipment, 
	CertificateOfOriginApplicationType.endorserParty-list.endorserParty, 
	CertificateOfOriginApplicationType.preparationParty, 
	CertificateOfOriginApplicationType.issuerParty, 
	CertificateOfOriginApplicationType.exporterParty, 
	CertificateOfOriginApplicationType.importerParty, 
	CertificateOfOriginApplicationType.issuingCountry, 
	CertificateOfOriginApplicationType.documentDistribution-list.documentDistribution,
	CertificateOfOriginApplicationType.supportingDocumentReference-list.supportingDocumentReference,
	CertificateOfOriginApplicationType.signature-list.signature, 
	ClassificationCategoryType.name, ClassificationCategoryType.codeValue,
	ClassificationCategoryType.description-list.description, 
	ClassificationCategoryType.categorizesClassificationCategory-list.categorizesClassificationCategory,
	ClassificationSchemeType.iD, ClassificationSchemeType.uUID, 
	ClassificationSchemeType.lastRevisionDate, 
	ClassificationSchemeType.lastRevisionTime, 
	ClassificationSchemeType.note-list.note, 
	ClassificationSchemeType.name, 
	ClassificationSchemeType.description-list.description, 
	ClassificationSchemeType.agencyID, 
	ClassificationSchemeType.agencyName, 
	ClassificationSchemeType.versionID, ClassificationSchemeType.uRI, 
	ClassificationSchemeType.schemeURI, 
	ClassificationSchemeType.languageID, 
	ClassificationSchemeType.classificationCategory-list.classificationCategory,
	CommodityClassificationType.natureCode, 
	CommodityClassificationType.cargoTypeCode, 
	CommodityClassificationType.commodityCode, 
	CommodityClassificationType.itemClassificationCode, 
	CommunicationType.channelCode, CommunicationType.channel, 
	CommunicationType.value, CompletedTaskType.annualAverageAmount, 
	CompletedTaskType.totalTaskAmount, 
	CompletedTaskType.partyCapacityAmount, 
	CompletedTaskType.description-list.description, 
	CompletedTaskType.evidenceSuppliedID, CompletedTaskType.period, 
	CompletedTaskType.recipientCustomerParty, ConsignmentType.iD, 
	ConsignmentType.carrierAssignedID, 
	ConsignmentType.consigneeAssignedID, 
	ConsignmentType.consignorAssignedID, 
	ConsignmentType.freightForwarderAssignedID, 
	ConsignmentType.brokerAssignedID, 
	ConsignmentType.contractedCarrierAssignedID, 
	ConsignmentType.performingCarrierAssignedID, 
	ConsignmentType.summaryDescription-list.summaryDescription, 
	ConsignmentType.totalInvoiceAmount, 
	ConsignmentType.declaredCustomsValueAmount, 
	ConsignmentType.tariffDescription-list.tariffDescription, 
	ConsignmentType.tariffCode, ConsignmentType.insurancePremiumAmount, 
	ConsignmentType.grossWeightMeasure, ConsignmentType.netWeightMeasure, 
	ConsignmentType.netNetWeightMeasure, 
	ConsignmentType.chargeableWeightMeasure, 
	ConsignmentType.grossVolumeMeasure, ConsignmentType.netVolumeMeasure, 
	ConsignmentType.loadingLengthMeasure, 
	ConsignmentType.remarks-list.remarks, 
	ConsignmentType.hazardousRiskIndicator, 
	ConsignmentType.animalFoodIndicator, 
	ConsignmentType.humanFoodIndicator, 
	ConsignmentType.livestockIndicator, 
	ConsignmentType.bulkCargoIndicator, 
	ConsignmentType.containerizedIndicator, 
	ConsignmentType.generalCargoIndicator, 
	ConsignmentType.specialSecurityIndicator, 
	ConsignmentType.thirdPartyPayerIndicator, 
	ConsignmentType.carrierServiceInstructions, 
	ConsignmentType.customsClearanceServiceInstructions, 
	ConsignmentType.forwarderServiceInstructions, 
	ConsignmentType.specialServiceInstructions, 
	ConsignmentType.sequenceID, ConsignmentType.shippingPriorityLevelCode,
	ConsignmentType.handlingCode, ConsignmentType.handlingInstructions, 
	ConsignmentType.information, ConsignmentType.totalGoodsItemQuantity, 
	ConsignmentType.totalTransportHandlingUnitQuantity, 
	ConsignmentType.insuranceValueAmount, 
	ConsignmentType.declaredForCarriageValueAmount, 
	ConsignmentType.declaredStatisticsValueAmount, 
	ConsignmentType.freeOnBoardValueAmount, 
	ConsignmentType.specialInstructions-list.specialInstructions, 
	ConsignmentType.splitConsignmentIndicator, 
	ConsignmentType.deliveryInstructions-list.deliveryInstructions, 
	ConsignmentType.consignmentQuantity, 
	ConsignmentType.consolidatableIndicator, 
	ConsignmentType.haulageInstructions-list.haulageInstructions, 
	ConsignmentType.loadingSequenceID, ConsignmentType.consigneeParty, 
	ConsignmentType.exporterParty, ConsignmentType.consignorParty, 
	ConsignmentType.importerParty, ConsignmentType.carrierParty, 
	ConsignmentType.freightForwarderParty, ConsignmentType.notifyParty, 
	ConsignmentType.originalDespatchParty, 
	ConsignmentType.finalDeliveryParty, 
	ConsignmentType.performingCarrierParty, 
	ConsignmentType.substituteCarrierParty, 
	ConsignmentType.logisticsOperatorParty, 
	ConsignmentType.transportAdvisorParty, 
	ConsignmentType.hazardousItemNotificationParty, 
	ConsignmentType.insuranceParty, ConsignmentType.mortgageHolderParty, 
	ConsignmentType.billOfLadingHolderParty, 
	ConsignmentType.originalDepartureCountry, 
	ConsignmentType.finalDestinationCountry, 
	ConsignmentType.transitCountry-list.transitCountry, 
	ConsignmentType.transportContract, 
	ConsignmentType.originalDespatchTransportationService, 
	ConsignmentType.finalDeliveryTransportationService, 
	ConsignmentType.deliveryTerms, ConsignmentType.paymentTerms, 
	ConsignmentType.collectPaymentTerms, 
	ConsignmentType.disbursementPaymentTerms, 
	ConsignmentType.prepaidPaymentTerms, 
	ConsignmentType.freightAllowanceCharge-list.freightAllowanceCharge, 
	ConsignmentType.extraAllowanceCharge-list.extraAllowanceCharge, 
	ConsignmentType.mainCarriageShipmentStage, 
	ConsignmentType.preCarriageShipmentStage-list.preCarriageShipmentStage,
	ConsignmentType.onCarriageShipmentStage-list.onCarriageShipmentStage, 
	ConsignmentType.transportHandlingUnit-list.transportHandlingUnit, 
	ConsignmentType.firstArrivalPortLocation, 
	ConsignmentType.lastExitPortLocation, 
	ConsignmentType.consolidatedShipment-list.consolidatedShipment, 
	ConsumptionType.utilityStatementTypeCode, ConsumptionType.mainPeriod, 
	ConsumptionType.allowanceCharge-list.allowanceCharge, 
	ConsumptionType.taxTotal-list.taxTotal, 
	ConsumptionType.energyWaterSupply, 
	ConsumptionType.telecommunicationsSupply, 
	ConsumptionType.legalMonetaryTotal, 
	ConsumptionAverageType.averageAmount, 
	ConsumptionAverageType.description, 
	ConsumptionHistoryType.meterNumber, ConsumptionHistoryType.quantity, 
	ConsumptionHistoryType.amount, 
	ConsumptionHistoryType.consumptionLevelCode, 
	ConsumptionHistoryType.consumptionLevel, 
	ConsumptionHistoryType.description-list.description, 
	ConsumptionHistoryType.period, ConsumptionLineType.iD, 
	ConsumptionLineType.parentDocumentLineReferenceID, 
	ConsumptionLineType.invoicedQuantity, 
	ConsumptionLineType.lineExtensionAmount, ConsumptionLineType.period, 
	ConsumptionLineType.delivery-list.delivery, 
	ConsumptionLineType.allowanceCharge-list.allowanceCharge, 
	ConsumptionLineType.taxTotal-list.taxTotal, 
	ConsumptionLineType.utilityItem, ConsumptionLineType.price, 
	ConsumptionLineType.unstructuredPrice, ConsumptionPointType.iD, 
	ConsumptionPointType.description, ConsumptionPointType.subscriberID, 
	ConsumptionPointType.subscriberTypeIdentifier, 
	ConsumptionPointType.subscriberTypeCode, 
	ConsumptionPointType.totalDeliveredQuantity, 
	ConsumptionPointType.address, ConsumptionPointType.webSiteAccess, 
	ConsumptionPointType.utilityMeter-list.utilityMeter, 
	ConsumptionReportType.iD, ConsumptionReportType.consumptionType, 
	ConsumptionReportType.consumptionTypeCode, 
	ConsumptionReportType.description-list.description, 
	ConsumptionReportType.totalConsumedQuantity, 
	ConsumptionReportType.basicConsumedQuantity, 
	ConsumptionReportType.residentOccupantsNumeric, 
	ConsumptionReportType.consumersEnergyLevelCode, 
	ConsumptionReportType.consumersEnergyLevel, 
	ConsumptionReportType.residenceType, 
	ConsumptionReportType.residenceTypeCode, 
	ConsumptionReportType.heatingType, 
	ConsumptionReportType.heatingTypeCode, ConsumptionReportType.period, 
	ConsumptionReportType.guidanceDocumentReference, 
	ConsumptionReportType.documentReference, 
	ConsumptionReportType.consumptionReportReference-list.consumptionReportReference,
	ConsumptionReportType.consumptionHistory-list.consumptionHistory, 
	ConsumptionReportReferenceType.consumptionReportID, 
	ConsumptionReportReferenceType.consumptionType, 
	ConsumptionReportReferenceType.consumptionTypeCode, 
	ConsumptionReportReferenceType.totalConsumedQuantity, 
	ConsumptionReportReferenceType.period, ContactType.iD, 
	ContactType.name, ContactType.telephone, ContactType.telefax, 
	ContactType.electronicMail, ContactType.note-list.note, 
	ContactType.otherCommunication-list.otherCommunication, 
	ContractType.iD, ContractType.issueDate, ContractType.issueTime, 
	ContractType.nominationDate, ContractType.nominationTime, 
	ContractType.contractTypeCode, ContractType.contractType, 
	ContractType.note-list.note, ContractType.versionID, 
	ContractType.description-list.description, 
	ContractType.validityPeriod, 
	ContractType.contractDocumentReference-list.contractDocumentReference,
	ContractType.nominationPeriod, ContractType.contractualDelivery, 
	ContractExecutionRequirementType.name-list.name, 
	ContractExecutionRequirementType.executionRequirementCode, 
	ContractExecutionRequirementType.description-list.description, 
	ContractExtensionType.optionsDescription-list.optionsDescription, 
	ContractExtensionType.minimumNumberNumeric, 
	ContractExtensionType.maximumNumberNumeric, 
	ContractExtensionType.optionValidityPeriod, 
	ContractExtensionType.renewal-list.renewal, 
	ContractingPartyType.contractingPartyTypeCode, 
	ContractingPartyType.activityCode-list.activityCode, 
	ContractingPartyType.buyerProfileURI, ContractingPartyType.party, 
	CorporateRegistrationSchemeType.iD, 
	CorporateRegistrationSchemeType.name, 
	CorporateRegistrationSchemeType.corporateRegistrationTypeCode, 
	CorporateRegistrationSchemeType.jurisdictionRegionAddress-list.jurisdictionRegionAddress,
	CorrectionType.correctionType, CorrectionType.correctionTypeCode, 
	CorrectionType.meterNumber, CorrectionType.gasPressureQuantity, 
	CorrectionType.actualTemperatureReductionQuantity, 
	CorrectionType.normalTemperatureReductionQuantity, 
	CorrectionType.differenceTemperatureReductionQuantity, 
	CorrectionType.description, CorrectionType.correctionUnitAmount, 
	CorrectionType.consumptionEnergyQuantity, 
	CorrectionType.consumptionWaterQuantity, 
	CorrectionType.correctionAmount, CountryType.identificationCode, 
	CountryType.name, CreditAccountType.accountID, CreditNoteLineType.iD, 
	CreditNoteLineType.uUID, CreditNoteLineType.note-list.note, 
	CreditNoteLineType.creditedQuantity, 
	CreditNoteLineType.lineExtensionAmount, 
	CreditNoteLineType.taxPointDate, 
	CreditNoteLineType.accountingCostCode, 
	CreditNoteLineType.accountingCost, 
	CreditNoteLineType.paymentPurposeCode, 
	CreditNoteLineType.freeOfChargeIndicator, 
	CreditNoteLineType.invoicePeriod-list.invoicePeriod, 
	CreditNoteLineType.orderLineReference-list.orderLineReference, 
	CreditNoteLineType.discrepancyResponse-list.discrepancyResponse, 
	CreditNoteLineType.despatchLineReference-list.despatchLineReference, 
	CreditNoteLineType.receiptLineReference-list.receiptLineReference, 
	CreditNoteLineType.billingReference-list.billingReference, 
	CreditNoteLineType.documentReference-list.documentReference, 
	CreditNoteLineType.pricingReference, 
	CreditNoteLineType.originatorParty, 
	CreditNoteLineType.delivery-list.delivery, 
	CreditNoteLineType.paymentTerms-list.paymentTerms, 
	CreditNoteLineType.taxTotal-list.taxTotal, 
	CreditNoteLineType.allowanceCharge-list.allowanceCharge, 
	CreditNoteLineType.item, CreditNoteLineType.price, 
	CreditNoteLineType.deliveryTerms-list.deliveryTerms, 
	CreditNoteLineType.subCreditNoteLine-list.subCreditNoteLine, 
	CustomerPartyType.customerAssignedAccountID, 
	CustomerPartyType.supplierAssignedAccountID, 
	CustomerPartyType.additionalAccountID-list.additionalAccountID, 
	CustomerPartyType.party, CustomerPartyType.deliveryContact, 
	CustomerPartyType.accountingContact, CustomerPartyType.buyerContact, 
	DebitNoteLineType.iD, DebitNoteLineType.uUID, 
	DebitNoteLineType.note-list.note, DebitNoteLineType.debitedQuantity, 
	DebitNoteLineType.lineExtensionAmount, DebitNoteLineType.taxPointDate,
	DebitNoteLineType.accountingCostCode, 
	DebitNoteLineType.accountingCost, 
	DebitNoteLineType.paymentPurposeCode, 
	DebitNoteLineType.discrepancyResponse-list.discrepancyResponse, 
	DebitNoteLineType.despatchLineReference-list.despatchLineReference, 
	DebitNoteLineType.receiptLineReference-list.receiptLineReference, 
	DebitNoteLineType.billingReference-list.billingReference, 
	DebitNoteLineType.documentReference-list.documentReference, 
	DebitNoteLineType.pricingReference, 
	DebitNoteLineType.delivery-list.delivery, 
	DebitNoteLineType.taxTotal-list.taxTotal, 
	DebitNoteLineType.allowanceCharge-list.allowanceCharge, 
	DebitNoteLineType.item, DebitNoteLineType.price, 
	DebitNoteLineType.subDebitNoteLine-list.subDebitNoteLine, 
	DeclarationType.name-list.name, DeclarationType.declarationTypeCode, 
	DeclarationType.description-list.description, 
	DeclarationType.evidenceSuppliedID-list.evidenceSuppliedID, 
	DeliveryType.iD, DeliveryType.quantity, DeliveryType.minimumQuantity, 
	DeliveryType.maximumQuantity, DeliveryType.actualDeliveryDate, 
	DeliveryType.actualDeliveryTime, DeliveryType.latestDeliveryDate, 
	DeliveryType.latestDeliveryTime, DeliveryType.releaseID, 
	DeliveryType.trackingID, DeliveryType.deliveryAddress, 
	DeliveryType.deliveryLocation, 
	DeliveryType.alternativeDeliveryLocation, 
	DeliveryType.requestedDeliveryPeriod, 
	DeliveryType.promisedDeliveryPeriod, 
	DeliveryType.estimatedDeliveryPeriod, DeliveryType.carrierParty, 
	DeliveryType.deliveryParty, DeliveryType.notifyParty-list.notifyParty,
	DeliveryType.despatch, DeliveryType.deliveryTerms-list.deliveryTerms, 
	DeliveryType.minimumDeliveryUnit, DeliveryType.maximumDeliveryUnit, 
	DeliveryType.shipment, DeliveryTermsType.iD, 
	DeliveryTermsType.specialTerms, 
	DeliveryTermsType.lossRiskResponsibilityCode, 
	DeliveryTermsType.lossRisk, DeliveryTermsType.amount, 
	DeliveryTermsType.deliveryLocation, DeliveryTermsType.allowanceCharge,
	DeliveryUnitType.batchQuantity, DeliveryUnitType.consumerUnitQuantity,
	DeliveryUnitType.hazardousRiskIndicator, 
	DependentPriceReferenceType.percent, 
	DependentPriceReferenceType.locationAddress, 
	DependentPriceReferenceType.dependentLineReference, DespatchType.iD, 
	DespatchType.requestedDespatchDate, 
	DespatchType.requestedDespatchTime, 
	DespatchType.estimatedDespatchDate, 
	DespatchType.estimatedDespatchTime, DespatchType.actualDespatchDate, 
	DespatchType.actualDespatchTime, DespatchType.guaranteedDespatchDate, 
	DespatchType.guaranteedDespatchTime, DespatchType.releaseID, 
	DespatchType.instructions, DespatchType.despatchAddress, 
	DespatchType.despatchLocation, DespatchType.despatchParty, 
	DespatchType.carrierParty, DespatchType.notifyParty-list.notifyParty, 
	DespatchType.contact, DespatchType.estimatedDespatchPeriod, 
	DespatchType.requestedDespatchPeriod, DespatchLineType.iD, 
	DespatchLineType.uUID, DespatchLineType.note-list.note, 
	DespatchLineType.lineStatusCode, DespatchLineType.deliveredQuantity, 
	DespatchLineType.backorderQuantity, DespatchLineType.backorderReason, 
	DespatchLineType.outstandingQuantity, 
	DespatchLineType.outstandingReason, 
	DespatchLineType.oversupplyQuantity, 
	DespatchLineType.orderLineReference-list.orderLineReference, 
	DespatchLineType.documentReference-list.documentReference, 
	DespatchLineType.item, DespatchLineType.shipment-list.shipment, 
	DimensionType.attributeID, DimensionType.measure, 
	DimensionType.description-list.description, 
	DimensionType.minimumMeasure, DimensionType.maximumMeasure, 
	DocumentDistributionType.printQualifier, 
	DocumentDistributionType.maximumCopiesNumeric, 
	DocumentDistributionType.party, DocumentReferenceType.iD, 
	DocumentReferenceType.copyIndicator, DocumentReferenceType.uUID, 
	DocumentReferenceType.issueDate, DocumentReferenceType.issueTime, 
	DocumentReferenceType.documentTypeCode, 
	DocumentReferenceType.documentType, 
	DocumentReferenceType.xPath-list.xPath, 
	DocumentReferenceType.languageID, DocumentReferenceType.localeCode, 
	DocumentReferenceType.versionID, 
	DocumentReferenceType.documentStatusCode, 
	DocumentReferenceType.documentDescription-list.documentDescription, 
	DocumentReferenceType.attachment, 
	DocumentReferenceType.validityPeriod, 
	DocumentReferenceType.issuerParty, 
	DocumentReferenceType.resultOfVerification, 
	DocumentResponseType.response, 
	DocumentResponseType.documentReference-list.documentReference, 
	DocumentResponseType.issuerParty, DocumentResponseType.recipientParty,
	DocumentResponseType.lineResponse-list.lineResponse, DutyType.amount, 
	DutyType.duty, DutyType.dutyCode, DutyType.taxCategory, 
	EconomicOperatorShortListType.limitationDescription-list.limitationDescription,
	EconomicOperatorShortListType.expectedQuantity, 
	EconomicOperatorShortListType.maximumQuantity, 
	EconomicOperatorShortListType.minimumQuantity, 
	EconomicOperatorShortListType.preSelectedParty-list.preSelectedParty, 
	EndorsementType.documentID, EndorsementType.approvalStatus, 
	EndorsementType.remarks-list.remarks, EndorsementType.endorserParty, 
	EndorsementType.signature-list.signature, EndorserPartyType.roleCode, 
	EndorserPartyType.sequenceNumeric, EndorserPartyType.party, 
	EndorserPartyType.signatoryContact, 
	EnergyTaxReportType.taxEnergyAmount, 
	EnergyTaxReportType.taxEnergyOnAccountAmount, 
	EnergyTaxReportType.taxEnergyBalanceAmount, 
	EnergyTaxReportType.taxScheme, 
	EnergyWaterSupplyType.consumptionReport-list.consumptionReport, 
	EnergyWaterSupplyType.energyTaxReport-list.energyTaxReport, 
	EnergyWaterSupplyType.consumptionAverage-list.consumptionAverage, 
	EnergyWaterSupplyType.energyWaterCorrection-list.energyWaterCorrection,
	EnvironmentalEmissionType.environmentalEmissionTypeCode, 
	EnvironmentalEmissionType.valueMeasure, 
	EnvironmentalEmissionType.description-list.description, 
	EvaluationCriteriaType.evaluationCriteriaTypeCode, 
	EvaluationCriteriaType.description-list.description, 
	EvaluationCriteriaType.thresholdAmount, 
	EvaluationCriteriaType.thresholdQuantity, 
	EvaluationCriteriaType.expressionCode-list.expressionCode, 
	EvaluationCriteriaType.durationPeriod, 
	EvaluationCriteriaType.suggestedEvidence-list.suggestedEvidence, 
	EventType.identificationID, EventType.occurrenceDate, 
	EventType.occurrenceTime, EventType.typeCode, 
	EventType.description-list.description, EventType.completionIndicator,
	EventType.currentStatus-list.currentStatus, 
	EventType.contact-list.contact, EventType.occurenceLocation, 
	EventCommentType.comment, EventCommentType.issueDate, 
	EventCommentType.issueTime, EventLineItemType.lineNumberNumeric, 
	EventLineItemType.participatingLocationsLocation, 
	EventLineItemType.retailPlannedImpact-list.retailPlannedImpact, 
	EventLineItemType.supplyItem, EventTacticType.comment, 
	EventTacticType.quantity, EventTacticType.eventTacticEnumeration, 
	EventTacticType.period, 
	EventTacticEnumerationType.consumerIncentiveTacticTypeCode, 
	EventTacticEnumerationType.displayTacticTypeCode, 
	EventTacticEnumerationType.featureTacticTypeCode, 
	EventTacticEnumerationType.tradeItemPackingLabelingTypeCode, 
	EvidenceType.iD, EvidenceType.evidenceTypeCode, 
	EvidenceType.name-list.name, EvidenceType.evidenceIssuingParty, 
	EvidenceType.documentReference, ExceptionCriteriaLineType.iD, 
	ExceptionCriteriaLineType.note-list.note, 
	ExceptionCriteriaLineType.thresholdValueComparisonCode, 
	ExceptionCriteriaLineType.thresholdQuantity, 
	ExceptionCriteriaLineType.exceptionStatusCode, 
	ExceptionCriteriaLineType.collaborationPriorityCode, 
	ExceptionCriteriaLineType.exceptionResolutionCode-list.exceptionResolutionCode,
	ExceptionCriteriaLineType.supplyChainActivityTypeCode, 
	ExceptionCriteriaLineType.performanceMetricTypeCode, 
	ExceptionCriteriaLineType.effectivePeriod, 
	ExceptionCriteriaLineType.supplyItem-list.supplyItem, 
	ExceptionCriteriaLineType.forecastExceptionCriteriaLine, 
	ExceptionNotificationLineType.iD, 
	ExceptionNotificationLineType.note-list.note, 
	ExceptionNotificationLineType.description, 
	ExceptionNotificationLineType.exceptionStatusCode, 
	ExceptionNotificationLineType.collaborationPriorityCode, 
	ExceptionNotificationLineType.resolutionCode, 
	ExceptionNotificationLineType.comparedValueMeasure, 
	ExceptionNotificationLineType.sourceValueMeasure, 
	ExceptionNotificationLineType.varianceQuantity, 
	ExceptionNotificationLineType.supplyChainActivityTypeCode, 
	ExceptionNotificationLineType.performanceMetricTypeCode, 
	ExceptionNotificationLineType.exceptionObservationPeriod, 
	ExceptionNotificationLineType.documentReference-list.documentReference,
	ExceptionNotificationLineType.forecastException, 
	ExceptionNotificationLineType.supplyItem, 
	ExchangeRateType.sourceCurrencyCode, 
	ExchangeRateType.sourceCurrencyBaseRate, 
	ExchangeRateType.targetCurrencyCode, 
	ExchangeRateType.targetCurrencyBaseRate, 
	ExchangeRateType.exchangeMarketID, ExchangeRateType.calculationRate, 
	ExchangeRateType.mathematicOperatorCode, ExchangeRateType.date, 
	ExchangeRateType.foreignExchangeContract, ExternalReferenceType.uRI, 
	ExternalReferenceType.documentHash, 
	ExternalReferenceType.hashAlgorithmMethod-list.hashAlgorithmMethod, 
	ExternalReferenceType.expiryDate, ExternalReferenceType.expiryTime, 
	ExternalReferenceType.mimeCode, ExternalReferenceType.formatCode, 
	ExternalReferenceType.encodingCode, 
	ExternalReferenceType.characterSetCode, 
	ExternalReferenceType.fileName, 
	ExternalReferenceType.description-list.description, 
	FinancialAccountType.iD, FinancialAccountType.name, 
	FinancialAccountType.aliasName, FinancialAccountType.accountTypeCode, 
	FinancialAccountType.accountFormatCode, 
	FinancialAccountType.currencyCode, 
	FinancialAccountType.paymentNote-list.paymentNote, 
	FinancialAccountType.financialInstitutionBranch, 
	FinancialAccountType.country, 
	FinancialGuaranteeType.guaranteeTypeCode, 
	FinancialGuaranteeType.description-list.description, 
	FinancialGuaranteeType.liabilityAmount, 
	FinancialGuaranteeType.amountRate, 
	FinancialGuaranteeType.constitutionPeriod, 
	FinancialInstitutionType.iD, FinancialInstitutionType.name, 
	FinancialInstitutionType.address, 
	ForecastExceptionType.forecastPurposeCode, 
	ForecastExceptionType.forecastTypeCode, 
	ForecastExceptionType.issueDate, ForecastExceptionType.issueTime, 
	ForecastExceptionType.dataSourceCode, 
	ForecastExceptionType.comparisonDataCode, 
	ForecastExceptionType.comparisonForecastIssueTime, 
	ForecastExceptionType.comparisonForecastIssueDate, 
	ForecastExceptionCriteriaLineType.forecastPurposeCode, 
	ForecastExceptionCriteriaLineType.forecastTypeCode, 
	ForecastExceptionCriteriaLineType.comparisonDataSourceCode, 
	ForecastExceptionCriteriaLineType.dataSourceCode, 
	ForecastExceptionCriteriaLineType.timeDeltaDaysQuantity, 
	ForecastLineType.iD, ForecastLineType.note-list.note, 
	ForecastLineType.frozenDocumentIndicator, 
	ForecastLineType.forecastTypeCode, ForecastLineType.forecastPeriod, 
	ForecastLineType.salesItem, ForecastRevisionLineType.iD, 
	ForecastRevisionLineType.note-list.note, 
	ForecastRevisionLineType.description, 
	ForecastRevisionLineType.revisedForecastLineID, 
	ForecastRevisionLineType.sourceForecastIssueDate, 
	ForecastRevisionLineType.sourceForecastIssueTime, 
	ForecastRevisionLineType.adjustmentReasonCode, 
	ForecastRevisionLineType.forecastPeriod, 
	ForecastRevisionLineType.salesItem, 
	FrameworkAgreementType.expectedOperatorQuantity, 
	FrameworkAgreementType.maximumOperatorQuantity, 
	FrameworkAgreementType.justification-list.justification, 
	FrameworkAgreementType.frequency-list.frequency, 
	FrameworkAgreementType.durationPeriod, 
	FrameworkAgreementType.subsequentProcessTenderRequirement-list.subsequentProcessTenderRequirement,
	GoodsItemType.iD, GoodsItemType.sequenceNumberID, 
	GoodsItemType.description-list.description, 
	GoodsItemType.hazardousRiskIndicator, 
	GoodsItemType.declaredCustomsValueAmount, 
	GoodsItemType.declaredForCarriageValueAmount, 
	GoodsItemType.declaredStatisticsValueAmount, 
	GoodsItemType.freeOnBoardValueAmount, 
	GoodsItemType.insuranceValueAmount, GoodsItemType.valueAmount, 
	GoodsItemType.grossWeightMeasure, GoodsItemType.netWeightMeasure, 
	GoodsItemType.netNetWeightMeasure, 
	GoodsItemType.chargeableWeightMeasure, 
	GoodsItemType.grossVolumeMeasure, GoodsItemType.netVolumeMeasure, 
	GoodsItemType.quantity, GoodsItemType.preferenceCriterionCode, 
	GoodsItemType.requiredCustomsID, GoodsItemType.customsStatusCode, 
	GoodsItemType.customsTariffQuantity, 
	GoodsItemType.customsImportClassifiedIndicator, 
	GoodsItemType.chargeableQuantity, GoodsItemType.returnableQuantity, 
	GoodsItemType.item-list.item, 
	GoodsItemType.goodsItemContainer-list.goodsItemContainer, 
	GoodsItemType.freightAllowanceCharge-list.freightAllowanceCharge, 
	GoodsItemType.invoiceLine-list.invoiceLine, 
	GoodsItemType.temperature-list.temperature, 
	GoodsItemType.containedGoodsItem-list.containedGoodsItem, 
	GoodsItemType.originAddress, GoodsItemType.delivery, 
	GoodsItemType.pickup, GoodsItemType.despatch, 
	GoodsItemType.measurementDimension-list.measurementDimension, 
	GoodsItemType.containingPackage-list.containingPackage, 
	GoodsItemType.shipmentDocumentReference, GoodsItemContainerType.iD, 
	GoodsItemContainerType.quantity, 
	GoodsItemContainerType.transportEquipment-list.transportEquipment, 
	HazardousGoodsTransitType.transportEmergencyCardCode, 
	HazardousGoodsTransitType.packingCriteriaCode, 
	HazardousGoodsTransitType.hazardousRegulationCode, 
	HazardousGoodsTransitType.inhalationToxicityZoneCode, 
	HazardousGoodsTransitType.transportAuthorizationCode, 
	HazardousGoodsTransitType.maximumTemperature, 
	HazardousGoodsTransitType.minimumTemperature, HazardousItemType.iD, 
	HazardousItemType.placardNotation, 
	HazardousItemType.placardEndorsement, 
	HazardousItemType.additionalInformation, HazardousItemType.uNDGCode, 
	HazardousItemType.emergencyProceduresCode, 
	HazardousItemType.medicalFirstAidGuideCode, 
	HazardousItemType.technicalName, HazardousItemType.categoryName, 
	HazardousItemType.hazardousCategoryCode, 
	HazardousItemType.upperOrangeHazardPlacardID, 
	HazardousItemType.lowerOrangeHazardPlacardID, 
	HazardousItemType.markingID, HazardousItemType.hazardClassID, 
	HazardousItemType.netWeightMeasure, 
	HazardousItemType.netVolumeMeasure, HazardousItemType.quantity, 
	HazardousItemType.contactParty, 
	HazardousItemType.secondaryHazard-list.secondaryHazard, 
	HazardousItemType.hazardousGoodsTransit-list.hazardousGoodsTransit, 
	HazardousItemType.emergencyTemperature, 
	HazardousItemType.flashpointTemperature, 
	HazardousItemType.additionalTemperature-list.additionalTemperature, 
	ImmobilizedSecurityType.immobilizationCertificateID, 
	ImmobilizedSecurityType.securityID, ImmobilizedSecurityType.issueDate,
	ImmobilizedSecurityType.faceValueAmount, 
	ImmobilizedSecurityType.marketValueAmount, 
	ImmobilizedSecurityType.sharesNumberQuantity, 
	ImmobilizedSecurityType.issuerParty, InstructionForReturnsLineType.iD,
	InstructionForReturnsLineType.note-list.note, 
	InstructionForReturnsLineType.quantity, 
	InstructionForReturnsLineType.manufacturerParty, 
	InstructionForReturnsLineType.item, InventoryReportLineType.iD, 
	InventoryReportLineType.note-list.note, 
	InventoryReportLineType.quantity, 
	InventoryReportLineType.inventoryValueAmount, 
	InventoryReportLineType.availabilityDate, 
	InventoryReportLineType.availabilityStatusCode, 
	InventoryReportLineType.item, InvoiceLineType.iD, 
	InvoiceLineType.uUID, InvoiceLineType.note-list.note, 
	InvoiceLineType.invoicedQuantity, InvoiceLineType.lineExtensionAmount,
	InvoiceLineType.taxPointDate, InvoiceLineType.accountingCostCode, 
	InvoiceLineType.accountingCost, InvoiceLineType.paymentPurposeCode, 
	InvoiceLineType.freeOfChargeIndicator, 
	InvoiceLineType.invoicePeriod-list.invoicePeriod, 
	InvoiceLineType.orderLineReference-list.orderLineReference, 
	InvoiceLineType.despatchLineReference-list.despatchLineReference, 
	InvoiceLineType.receiptLineReference-list.receiptLineReference, 
	InvoiceLineType.billingReference-list.billingReference, 
	InvoiceLineType.documentReference-list.documentReference, 
	InvoiceLineType.pricingReference, InvoiceLineType.originatorParty, 
	InvoiceLineType.delivery-list.delivery, 
	InvoiceLineType.paymentTerms-list.paymentTerms, 
	InvoiceLineType.allowanceCharge-list.allowanceCharge, 
	InvoiceLineType.taxTotal-list.taxTotal, InvoiceLineType.item, 
	InvoiceLineType.price, InvoiceLineType.deliveryTerms, 
	InvoiceLineType.subInvoiceLine-list.subInvoiceLine, 
	ItemType.description-list.description, ItemType.packQuantity, 
	ItemType.packSizeNumeric, ItemType.catalogueIndicator, ItemType.name, 
	ItemType.hazardousRiskIndicator, ItemType.additionalInformation, 
	ItemType.keyword-list.keyword, ItemType.brandName-list.brandName, 
	ItemType.modelName-list.modelName, ItemType.buyersItemIdentification, 
	ItemType.sellersItemIdentification, 
	ItemType.manufacturersItemIdentification-list.manufacturersItemIdentification,
	ItemType.standardItemIdentification, 
	ItemType.catalogueItemIdentification, 
	ItemType.additionalItemIdentification-list.additionalItemIdentification,
	ItemType.catalogueDocumentReference, 
	ItemType.itemSpecificationDocumentReference-list.itemSpecificationDocumentReference,
	ItemType.originCountry, 
	ItemType.commodityClassification-list.commodityClassification, 
	ItemType.transactionConditions-list.transactionConditions, 
	ItemType.hazardousItem-list.hazardousItem, 
	ItemType.classifiedTaxCategory-list.classifiedTaxCategory, 
	ItemType.additionalItemProperty-list.additionalItemProperty, 
	ItemType.manufacturerParty-list.manufacturerParty, 
	ItemType.informationContentProviderParty, 
	ItemType.originAddress-list.originAddress, 
	ItemType.itemInstance-list.itemInstance, 
	ItemType.certificate-list.certificate, 
	ItemType.dimension-list.dimension, ItemComparisonType.priceAmount, 
	ItemComparisonType.quantity, ItemIdentificationType.iD, 
	ItemIdentificationType.extendedID, 
	ItemIdentificationType.physicalAttribute-list.physicalAttribute, 
	ItemIdentificationType.measurementDimension-list.measurementDimension,
	ItemIdentificationType.issuerParty, 
	ItemInformationRequestLineType.timeFrequencyCode, 
	ItemInformationRequestLineType.supplyChainActivityTypeCode, 
	ItemInformationRequestLineType.forecastTypeCode, 
	ItemInformationRequestLineType.performanceMetricTypeCode, 
	ItemInformationRequestLineType.period-list.period, 
	ItemInformationRequestLineType.salesItem-list.salesItem, 
	ItemInstanceType.productTraceID, ItemInstanceType.manufactureDate, 
	ItemInstanceType.manufactureTime, ItemInstanceType.bestBeforeDate, 
	ItemInstanceType.registrationID, ItemInstanceType.serialID, 
	ItemInstanceType.additionalItemProperty-list.additionalItemProperty, 
	ItemInstanceType.lotIdentification, 
	ItemLocationQuantityType.leadTimeMeasure, 
	ItemLocationQuantityType.minimumQuantity, 
	ItemLocationQuantityType.maximumQuantity, 
	ItemLocationQuantityType.hazardousRiskIndicator, 
	ItemLocationQuantityType.tradingRestrictions-list.tradingRestrictions,
	ItemLocationQuantityType.applicableTerritoryAddress-list.applicableTerritoryAddress,
	ItemLocationQuantityType.price, 
	ItemLocationQuantityType.deliveryUnit-list.deliveryUnit, 
	ItemLocationQuantityType.applicableTaxCategory-list.applicableTaxCategory,
	ItemLocationQuantityType.package, 
	ItemLocationQuantityType.allowanceCharge-list.allowanceCharge, 
	ItemLocationQuantityType.dependentPriceReference, 
	ItemManagementProfileType.frozenPeriodDaysNumeric, 
	ItemManagementProfileType.minimumInventoryQuantity, 
	ItemManagementProfileType.multipleOrderQuantity, 
	ItemManagementProfileType.orderIntervalDaysNumeric, 
	ItemManagementProfileType.replenishmentOwnerDescription, 
	ItemManagementProfileType.targetServicePercent, 
	ItemManagementProfileType.targetInventoryQuantity, 
	ItemManagementProfileType.effectivePeriod, 
	ItemManagementProfileType.item, 
	ItemManagementProfileType.itemLocationQuantity, ItemPropertyType.iD, 
	ItemPropertyType.name, ItemPropertyType.nameCode, 
	ItemPropertyType.testMethod, ItemPropertyType.value, 
	ItemPropertyType.valueQuantity, 
	ItemPropertyType.valueQualifier-list.valueQualifier, 
	ItemPropertyType.importanceCode, 
	ItemPropertyType.listValue-list.listValue, 
	ItemPropertyType.usabilityPeriod, 
	ItemPropertyType.itemPropertyGroup-list.itemPropertyGroup, 
	ItemPropertyType.rangeDimension, ItemPropertyType.itemPropertyRange, 
	ItemPropertyGroupType.iD, ItemPropertyGroupType.name, 
	ItemPropertyGroupType.importanceCode, 
	ItemPropertyRangeType.minimumValue, 
	ItemPropertyRangeType.maximumValue, LanguageType.iD, 
	LanguageType.name, LanguageType.localeCode, LineItemType.iD, 
	LineItemType.salesOrderID, LineItemType.uUID, 
	LineItemType.note-list.note, LineItemType.lineStatusCode, 
	LineItemType.quantity, LineItemType.lineExtensionAmount, 
	LineItemType.totalTaxAmount, LineItemType.minimumQuantity, 
	LineItemType.maximumQuantity, LineItemType.minimumBackorderQuantity, 
	LineItemType.maximumBackorderQuantity, 
	LineItemType.inspectionMethodCode, 
	LineItemType.partialDeliveryIndicator, 
	LineItemType.backOrderAllowedIndicator, 
	LineItemType.accountingCostCode, LineItemType.accountingCost, 
	LineItemType.warrantyInformation-list.warrantyInformation, 
	LineItemType.delivery-list.delivery, LineItemType.deliveryTerms, 
	LineItemType.originatorParty, 
	LineItemType.orderedShipment-list.orderedShipment, 
	LineItemType.pricingReference, 
	LineItemType.allowanceCharge-list.allowanceCharge, LineItemType.price,
	LineItemType.item, LineItemType.subLineItem-list.subLineItem, 
	LineItemType.warrantyValidityPeriod, LineItemType.warrantyParty, 
	LineReferenceType.lineID, LineReferenceType.uUID, 
	LineReferenceType.lineStatusCode, LineReferenceType.documentReference,
	LineResponseType.lineReference, 
	LineResponseType.response-list.response, LocationType.iD, 
	LocationType.description, LocationType.conditions, 
	LocationType.countrySubentity, LocationType.countrySubentityCode, 
	LocationType.locationTypeCode, LocationType.informationURI, 
	LocationType.validityPeriod-list.validityPeriod, LocationType.address,
	LocationType.subsidiaryLocation-list.subsidiaryLocation, 
	LocationType.locationCoordinate-list.locationCoordinate, 
	LocationCoordinateType.coordinateSystemCode, 
	LocationCoordinateType.latitudeDegreesMeasure, 
	LocationCoordinateType.latitudeMinutesMeasure, 
	LocationCoordinateType.latitudeDirectionCode, 
	LocationCoordinateType.longitudeDegreesMeasure, 
	LocationCoordinateType.longitudeMinutesMeasure, 
	LocationCoordinateType.longitudeDirectionCode, 
	LocationCoordinateType.altitudeMeasure, 
	LotIdentificationType.lotNumberID, LotIdentificationType.expiryDate, 
	LotIdentificationType.additionalItemProperty-list.additionalItemProperty,
	MaritimeTransportType.vesselID, MaritimeTransportType.vesselName, 
	MeterType.meterNumber, MeterType.meterName, MeterType.meterConstant, 
	MeterType.meterConstantCode, MeterType.totalDeliveredQuantity, 
	MeterType.meterReading-list.meterReading, 
	MeterType.meterProperty-list.meterProperty, MeterPropertyType.name, 
	MeterPropertyType.nameCode, MeterPropertyType.value-list.value, 
	MeterPropertyType.valueQuantity, 
	MeterPropertyType.valueQualifier-list.valueQualifier, 
	MeterReadingType.meterReadingType, 
	MeterReadingType.meterReadingTypeCode, 
	MeterReadingType.previousMeterReadingDate, 
	MeterReadingType.previousMeterQuantity, 
	MeterReadingType.latestMeterReadingDate, 
	MeterReadingType.latestMeterQuantity, 
	MeterReadingType.meterReadingMethod, 
	MeterReadingType.meterReadingMethodCode, 
	MeterReadingType.meterReadingComments-list.meterReadingComments, 
	MeterReadingType.deliveredQuantity, 
	MiscellaneousEventType.miscellaneousEventTypeCode, 
	MiscellaneousEventType.eventLineItem-list.eventLineItem, 
	MonetaryTotalType.lineExtensionAmount, 
	MonetaryTotalType.taxExclusiveAmount, 
	MonetaryTotalType.taxInclusiveAmount, 
	MonetaryTotalType.allowanceTotalAmount, 
	MonetaryTotalType.chargeTotalAmount, MonetaryTotalType.prepaidAmount, 
	MonetaryTotalType.payableRoundingAmount, 
	MonetaryTotalType.payableAmount, 
	MonetaryTotalType.payableAlternativeAmount, 
	NotificationRequirementType.notificationTypeCode, 
	NotificationRequirementType.notifyParty-list.notifyParty, 
	NotificationRequirementType.preEventPeriod, 
	NotificationRequirementType.postEventPeriod, 
	OnAccountPaymentType.estimatedConsumedQuantity, 
	OnAccountPaymentType.note, 
	OnAccountPaymentType.paymentTerms-list.paymentTerms, 
	OrderLineType.substitutionStatusCode, OrderLineType.note-list.note, 
	OrderLineType.lineItem, OrderLineType.sellerProposedSubstituteLineItem-list.sellerProposedSubstituteLineItem,
	OrderLineType.sellerSubstitutedLineItem-list.sellerSubstitutedLineItem,
	OrderLineType.buyerProposedSubstituteLineItem-list.buyerProposedSubstituteLineItem,
	OrderLineType.catalogueLineReference, 
	OrderLineType.quotationLineReference, 
	OrderLineType.documentReference-list.documentReference, 
	OrderLineReferenceType.lineID, 
	OrderLineReferenceType.salesOrderLineID, OrderLineReferenceType.uUID, 
	OrderLineReferenceType.lineStatusCode, 
	OrderLineReferenceType.orderReference, OrderReferenceType.iD, 
	OrderReferenceType.salesOrderID, OrderReferenceType.copyIndicator, 
	OrderReferenceType.uUID, OrderReferenceType.issueDate, 
	OrderReferenceType.issueTime, OrderReferenceType.customerReference, 
	OrderReferenceType.orderTypeCode, 
	OrderReferenceType.documentReference, OrderedShipmentType.shipment, 
	OrderedShipmentType.package-list.package, PackageType.iD, 
	PackageType.quantity, PackageType.returnableMaterialIndicator, 
	PackageType.packageLevelCode, PackageType.packagingTypeCode, 
	PackageType.packingMaterial-list.packingMaterial, PackageType.traceID,
	PackageType.containedPackage-list.containedPackage, 
	PackageType.containingTransportEquipment, 
	PackageType.goodsItem-list.goodsItem, 
	PackageType.measurementDimension-list.measurementDimension, 
	PackageType.deliveryUnit-list.deliveryUnit, PackageType.delivery, 
	PackageType.pickup, PackageType.despatch, PartyType.markCareIndicator,
	PartyType.markAttentionIndicator, PartyType.websiteURI, 
	PartyType.logoReferenceID, PartyType.endpointID, 
	PartyType.industryClassificationCode, 
	PartyType.partyIdentification-list.partyIdentification, 
	PartyType.partyName-list.partyName, PartyType.language, 
	PartyType.postalAddress, PartyType.physicalLocation, 
	PartyType.partyTaxScheme-list.partyTaxScheme, 
	PartyType.partyLegalEntity-list.partyLegalEntity, PartyType.contact, 
	PartyType.person-list.person, PartyType.agentParty, 
	PartyType.serviceProviderParty-list.serviceProviderParty, 
	PartyType.powerOfAttorney-list.powerOfAttorney, 
	PartyType.financialAccount, PartyIdentificationType.iD, 
	PartyLegalEntityType.registrationName, PartyLegalEntityType.companyID,
	PartyLegalEntityType.registrationDate, 
	PartyLegalEntityType.registrationExpirationDate, 
	PartyLegalEntityType.companyLegalFormCode, 
	PartyLegalEntityType.soleProprietorshipIndicator, 
	PartyLegalEntityType.companyLiquidationStatusCode, 
	PartyLegalEntityType.corporateStockAmount, 
	PartyLegalEntityType.fullyPaidSharesIndicator, 
	PartyLegalEntityType.registrationAddress, 
	PartyLegalEntityType.corporateRegistrationScheme, 
	PartyLegalEntityType.headParty, 
	PartyLegalEntityType.shareholderParty-list.shareholderParty, 
	PartyNameType.name, PartyTaxSchemeType.registrationName, 
	PartyTaxSchemeType.companyID, PartyTaxSchemeType.taxLevelCode, 
	PartyTaxSchemeType.exemptionReasonCode, 
	PartyTaxSchemeType.exemptionReason, 
	PartyTaxSchemeType.registrationAddress, PartyTaxSchemeType.taxScheme, 
	PaymentType.iD, PaymentType.paidAmount, PaymentType.receivedDate, 
	PaymentType.paidDate, PaymentType.paidTime, PaymentType.instructionID,
	PaymentMandateType.iD, PaymentMandateType.mandateTypeCode, 
	PaymentMandateType.clause-list.clause, 
	PaymentMandateType.clauseCode-list.clauseCode, 
	PaymentMandateType.maximumPaymentInstructionsNumeric, 
	PaymentMandateType.maximumPaidAmount, PaymentMandateType.signatureID, 
	PaymentMandateType.payerParty, 
	PaymentMandateType.payerFinancialAccount, 
	PaymentMandateType.validityPeriod, 
	PaymentMandateType.paymentReversalPeriod, PaymentMeansType.iD, 
	PaymentMeansType.paymentMeansCode, PaymentMeansType.paymentDueDate, 
	PaymentMeansType.paymentChannelCode, PaymentMeansType.instructionID, 
	PaymentMeansType.instructionNote-list.instructionNote, 
	PaymentMeansType.paymentID-list.paymentID, 
	PaymentMeansType.cardAccount, PaymentMeansType.payerFinancialAccount, 
	PaymentMeansType.payeeFinancialAccount, 
	PaymentMeansType.creditAccount, PaymentMeansType.paymentMandate, 
	PaymentMeansType.tradeFinancing, PaymentTermsType.iD, 
	PaymentTermsType.paymentMeansID-list.paymentMeansID, 
	PaymentTermsType.prepaidPaymentReferenceID, 
	PaymentTermsType.note-list.note, PaymentTermsType.referenceEventCode, 
	PaymentTermsType.settlementDiscountPercent, 
	PaymentTermsType.penaltySurchargePercent, 
	PaymentTermsType.paymentPercent, PaymentTermsType.amount, 
	PaymentTermsType.settlementDiscountAmount, 
	PaymentTermsType.penaltyAmount, 
	PaymentTermsType.paymentTermsDetailsURI, 
	PaymentTermsType.paymentDueDate, PaymentTermsType.installmentDueDate, 
	PaymentTermsType.invoicingPartyReference, 
	PaymentTermsType.settlementPeriod, PaymentTermsType.penaltyPeriod, 
	PaymentTermsType.exchangeRate, PaymentTermsType.validityPeriod, 
	PerformanceDataLineType.iD, PerformanceDataLineType.note-list.note, 
	PerformanceDataLineType.performanceValueQuantity, 
	PerformanceDataLineType.performanceMetricTypeCode, 
	PerformanceDataLineType.period, PerformanceDataLineType.item, 
	PeriodType.startDate, PeriodType.startTime, PeriodType.endDate, 
	PeriodType.endTime, PeriodType.durationMeasure, 
	PeriodType.descriptionCode-list.descriptionCode, 
	PeriodType.description-list.description, PersonType.iD, 
	PersonType.firstName, PersonType.familyName, PersonType.title, 
	PersonType.middleName, PersonType.nameSuffix, PersonType.jobTitle, 
	PersonType.nationalityID, PersonType.genderCode, PersonType.birthDate,
	PersonType.organizationDepartment, PersonType.contact, 
	PersonType.financialAccount, PersonType.identityDocumentReference, 
	PhysicalAttributeType.attributeID, PhysicalAttributeType.positionCode,
	PhysicalAttributeType.descriptionCode, 
	PhysicalAttributeType.description-list.description, PickupType.iD, 
	PickupType.actualPickupDate, PickupType.actualPickupTime, 
	PickupType.earliestPickupDate, PickupType.earliestPickupTime, 
	PickupType.latestPickupDate, PickupType.latestPickupTime, 
	PickupType.pickupLocation, PickupType.pickupParty, 
	PowerOfAttorneyType.iD, PowerOfAttorneyType.issueDate, 
	PowerOfAttorneyType.issueTime, 
	PowerOfAttorneyType.description-list.description, 
	PowerOfAttorneyType.notaryParty, PowerOfAttorneyType.agentParty, 
	PowerOfAttorneyType.mandateDocumentReference-list.mandateDocumentReference,
	PriceType.priceAmount, PriceType.baseQuantity, 
	PriceType.priceChangeReason-list.priceChangeReason, 
	PriceType.priceTypeCode, PriceType.priceType, 
	PriceType.orderableUnitFactorRate, 
	PriceType.validityPeriod-list.validityPeriod, PriceType.priceList, 
	PriceType.allowanceCharge-list.allowanceCharge, 
	PriceType.pricingExchangeRate, PriceListType.iD, 
	PriceListType.statusCode, 
	PriceListType.validityPeriod-list.validityPeriod, 
	PriceListType.previousPriceList, 
	PricingReferenceType.originalItemLocationQuantity, 
	PricingReferenceType.alternativeConditionPrice-list.alternativeConditionPrice,
	ProcessJustificationType.previousCancellationReasonCode, 
	ProcessJustificationType.processReasonCode, 
	ProcessJustificationType.processReason-list.processReason, 
	ProcessJustificationType.description-list.description, 
	ProcurementProjectType.iD, ProcurementProjectType.name-list.name, 
	ProcurementProjectType.description-list.description, 
	ProcurementProjectType.procurementTypeCode, 
	ProcurementProjectType.procurementSubTypeCode, 
	ProcurementProjectType.qualityControlCode, 
	ProcurementProjectType.requiredFeeAmount, 
	ProcurementProjectType.feeDescription-list.feeDescription, 
	ProcurementProjectType.requestedDeliveryDate, 
	ProcurementProjectType.estimatedOverallContractQuantity, 
	ProcurementProjectType.budgetAmount, 
	ProcurementProjectType.requiredCommodityClassification-list.requiredCommodityClassification,
	ProcurementProjectType.realizedLocation-list.realizedLocation, 
	ProcurementProjectType.plannedPeriod, 
	ProcurementProjectType.contractExtension, 
	ProcurementProjectType.requestForTenderLine-list.requestForTenderLine,
	ProcurementProjectLotType.iD, 
	ProcurementProjectLotType.tenderingTerms, 
	ProcurementProjectLotType.procurementProject, 
	PromotionalEventType.promotionalEventTypeCode, 
	PromotionalEventType.submissionDate, 
	PromotionalEventType.firstShipmentAvailibilityDate, 
	PromotionalEventType.latestProposalAcceptanceDate, 
	PromotionalEventType.promotionalSpecification-list.promotionalSpecification,
	PromotionalEventLineItemType.amount, 
	PromotionalEventLineItemType.eventLineItem, 
	PromotionalSpecificationType.specificationID, 
	PromotionalSpecificationType.promotionalEventLineItem-list.promotionalEventLineItem,
	PromotionalSpecificationType.eventTactic-list.eventTactic, 
	QualificationResolutionType.admissionCode, 
	QualificationResolutionType.procurementProjectLotID, 
	QualificationResolutionType.exclusionReason-list.exclusionReason, 
	QualificationResolutionType.resolution-list.resolution, 
	QualificationResolutionType.resolutionDate, 
	QualificationResolutionType.resolutionTime, 
	QualifyingPartyType.participationPercent, 
	QualifyingPartyType.personalSituation-list.personalSituation, 
	QualifyingPartyType.operatingYearsQuantity, 
	QualifyingPartyType.employeeQuantity, 
	QualifyingPartyType.businessClassificationEvidenceID, 
	QualifyingPartyType.businessIdentityEvidenceID, 
	QualifyingPartyType.businessClassificationScheme, 
	QualifyingPartyType.technicalCapability-list.technicalCapability, 
	QualifyingPartyType.financialCapability-list.financialCapability, 
	QualifyingPartyType.completedTask-list.completedTask, 
	QualifyingPartyType.declaration-list.declaration, 
	QualifyingPartyType.party, QuotationLineType.iD, 
	QuotationLineType.note-list.note, QuotationLineType.quantity, 
	QuotationLineType.lineExtensionAmount, 
	QuotationLineType.totalTaxAmount, 
	QuotationLineType.requestForQuotationLineID, 
	QuotationLineType.documentReference-list.documentReference, 
	QuotationLineType.lineItem, 
	QuotationLineType.sellerProposedSubstituteLineItem-list.sellerProposedSubstituteLineItem,
	QuotationLineType.alternativeLineItem-list.alternativeLineItem, 
	QuotationLineType.requestLineReference, RailTransportType.trainID, 
	RailTransportType.railCarID, ReceiptLineType.iD, ReceiptLineType.uUID,
	ReceiptLineType.note-list.note, ReceiptLineType.receivedQuantity, 
	ReceiptLineType.shortQuantity, ReceiptLineType.shortageActionCode, 
	ReceiptLineType.rejectedQuantity, ReceiptLineType.rejectReasonCode, 
	ReceiptLineType.rejectReason, ReceiptLineType.rejectActionCode, 
	ReceiptLineType.quantityDiscrepancyCode, 
	ReceiptLineType.oversupplyQuantity, ReceiptLineType.receivedDate, 
	ReceiptLineType.timingComplaintCode, ReceiptLineType.timingComplaint, 
	ReceiptLineType.orderLineReference, 
	ReceiptLineType.despatchLineReference-list.despatchLineReference, 
	ReceiptLineType.documentReference-list.documentReference, 
	ReceiptLineType.item-list.item, 
	ReceiptLineType.shipment-list.shipment, RegulationType.name-list.name,
	RegulationType.legalReference, RegulationType.ontologyURI, 
	RelatedItemType.iD, RelatedItemType.quantity, 
	RelatedItemType.description-list.description, ReminderLineType.iD, 
	ReminderLineType.note-list.note, ReminderLineType.uUID, 
	ReminderLineType.balanceBroughtForwardIndicator, 
	ReminderLineType.debitLineAmount, ReminderLineType.creditLineAmount, 
	ReminderLineType.accountingCostCode, ReminderLineType.accountingCost, 
	ReminderLineType.penaltySurchargePercent, ReminderLineType.amount, 
	ReminderLineType.paymentPurposeCode, 
	ReminderLineType.reminderPeriod-list.reminderPeriod, 
	ReminderLineType.billingReference-list.billingReference, 
	ReminderLineType.exchangeRate, RemittanceAdviceLineType.iD, 
	RemittanceAdviceLineType.note-list.note, 
	RemittanceAdviceLineType.uUID, 
	RemittanceAdviceLineType.debitLineAmount, 
	RemittanceAdviceLineType.creditLineAmount, 
	RemittanceAdviceLineType.balanceAmount, 
	RemittanceAdviceLineType.paymentPurposeCode, 
	RemittanceAdviceLineType.invoicingPartyReference, 
	RemittanceAdviceLineType.accountingSupplierParty, 
	RemittanceAdviceLineType.accountingCustomerParty, 
	RemittanceAdviceLineType.buyerCustomerParty, 
	RemittanceAdviceLineType.sellerSupplierParty, 
	RemittanceAdviceLineType.originatorCustomerParty, 
	RemittanceAdviceLineType.payeeParty, 
	RemittanceAdviceLineType.invoicePeriod-list.invoicePeriod, 
	RemittanceAdviceLineType.billingReference-list.billingReference, 
	RemittanceAdviceLineType.documentReference-list.documentReference, 
	RemittanceAdviceLineType.exchangeRate, RenewalType.amount, 
	RenewalType.period, RequestForQuotationLineType.iD, 
	RequestForQuotationLineType.uUID, 
	RequestForQuotationLineType.note-list.note, 
	RequestForQuotationLineType.optionalLineItemIndicator, 
	RequestForQuotationLineType.privacyCode, 
	RequestForQuotationLineType.securityClassificationCode, 
	RequestForQuotationLineType.documentReference-list.documentReference, 
	RequestForQuotationLineType.lineItem, RequestForTenderLineType.iD, 
	RequestForTenderLineType.uUID, 
	RequestForTenderLineType.note-list.note, 
	RequestForTenderLineType.quantity, 
	RequestForTenderLineType.minimumQuantity, 
	RequestForTenderLineType.maximumQuantity, 
	RequestForTenderLineType.maximumTaxExclusiveAmount, 
	RequestForTenderLineType.maximumTaxInclusiveAmount, 
	RequestForTenderLineType.documentReference-list.documentReference, 
	RequestForTenderLineType.deliveryPeriod-list.deliveryPeriod, 
	RequestForTenderLineType.requiredItemLocationQuantity-list.requiredItemLocationQuantity,
	RequestForTenderLineType.warrantyValidityPeriod, 
	RequestForTenderLineType.item, 
	RequestForTenderLineType.subRequestForTenderLine-list.subRequestForTenderLine,
	ResponseType.referenceID, ResponseType.responseCode, 
	ResponseType.description-list.description, ResponseType.effectiveDate,
	ResponseType.effectiveTime, ResponseType.status, 
	ResultOfVerificationType.validatorID, 
	ResultOfVerificationType.validationResultCode, 
	ResultOfVerificationType.validationDate, 
	ResultOfVerificationType.validationTime, 
	ResultOfVerificationType.validateProcess, 
	ResultOfVerificationType.validateTool, 
	ResultOfVerificationType.validateToolVersion, 
	ResultOfVerificationType.signatoryParty, 
	RetailPlannedImpactType.amount, 
	RetailPlannedImpactType.forecastPurposeCode, 
	RetailPlannedImpactType.forecastTypeCode, 
	RetailPlannedImpactType.period, RoadTransportType.licensePlateID, 
	SalesItemType.quantity, 
	SalesItemType.activityProperty-list.activityProperty, 
	SalesItemType.taxExclusivePrice-list.taxExclusivePrice, 
	SalesItemType.taxInclusivePrice-list.taxInclusivePrice, 
	SalesItemType.item, SecondaryHazardType.iD, 
	SecondaryHazardType.placardNotation, 
	SecondaryHazardType.placardEndorsement, 
	SecondaryHazardType.emergencyProceduresCode, 
	SecondaryHazardType.extension, ServicePointType.sequenceNumberID, 
	ServicePointType.transportModeCode, 
	ServicePointType.remarks-list.remarks, 
	ServicePointType.servicePointLocation, 
	ServicePointType.transportMeans, 
	ServicePointType.plannedDeparturePeriod, 
	ServicePointType.plannedArrivalPeriod, 
	ServicePointType.despatchPeriod, ServicePointType.deliveryPeriod, 
	ServiceProviderPartyType.iD, ServiceProviderPartyType.serviceTypeCode,
	ServiceProviderPartyType.serviceType-list.serviceType, 
	ServiceProviderPartyType.party, 
	ServiceProviderPartyType.sellerContact, 
	ShareholderPartyType.partecipationPercent, ShareholderPartyType.party,
	ShipmentType.iD, ShipmentType.shippingPriorityLevelCode, 
	ShipmentType.handlingCode, ShipmentType.handlingInstructions, 
	ShipmentType.information, ShipmentType.grossWeightMeasure, 
	ShipmentType.netWeightMeasure, ShipmentType.netNetWeightMeasure, 
	ShipmentType.grossVolumeMeasure, ShipmentType.netVolumeMeasure, 
	ShipmentType.totalGoodsItemQuantity, 
	ShipmentType.totalTransportHandlingUnitQuantity, 
	ShipmentType.insuranceValueAmount, 
	ShipmentType.declaredCustomsValueAmount, 
	ShipmentType.declaredForCarriageValueAmount, 
	ShipmentType.declaredStatisticsValueAmount, 
	ShipmentType.freeOnBoardValueAmount, 
	ShipmentType.specialInstructions-list.specialInstructions, 
	ShipmentType.deliveryInstructions-list.deliveryInstructions, 
	ShipmentType.splitConsignmentIndicator, 
	ShipmentType.consignmentQuantity, 
	ShipmentType.consignment-list.consignment, 
	ShipmentType.goodsItem-list.goodsItem, 
	ShipmentType.shipmentStage-list.shipmentStage, ShipmentType.delivery, 
	ShipmentType.transportHandlingUnit-list.transportHandlingUnit, 
	ShipmentType.returnAddress, ShipmentType.originAddress, 
	ShipmentType.firstArrivalPortLocation, 
	ShipmentType.lastExitPortLocation, ShipmentType.exportCountry, 
	ShipmentType.freightAllowanceCharge-list.freightAllowanceCharge, 
	ShipmentStageType.iD, ShipmentStageType.transportModeCode, 
	ShipmentStageType.transportMeansTypeCode, 
	ShipmentStageType.transitDirectionCode, 
	ShipmentStageType.preCarriageIndicator, 
	ShipmentStageType.onCarriageIndicator, 
	ShipmentStageType.estimatedDeliveryDate, 
	ShipmentStageType.estimatedDeliveryTime, 
	ShipmentStageType.requiredDeliveryDate, 
	ShipmentStageType.requiredDeliveryTime, 
	ShipmentStageType.loadingSequenceID, 
	ShipmentStageType.successiveSequenceID, 
	ShipmentStageType.instructions, 
	ShipmentStageType.demurrageInstructions, 
	ShipmentStageType.transitPeriod, 
	ShipmentStageType.carrierParty-list.carrierParty, 
	ShipmentStageType.transportMeans, 
	ShipmentStageType.loadingPortLocation, 
	ShipmentStageType.unloadingPortLocation, 
	ShipmentStageType.transshipPortLocation, 
	ShipmentStageType.loadingTransportEvent, 
	ShipmentStageType.examinationTransportEvent, 
	ShipmentStageType.availabilityTransportEvent, 
	ShipmentStageType.exportationTransportEvent, 
	ShipmentStageType.dischargeTransportEvent, 
	ShipmentStageType.warehousingTransportEvent, 
	ShipmentStageType.takeoverTransportEvent, 
	ShipmentStageType.optionalTakeoverTransportEvent, 
	ShipmentStageType.dropoffTransportEvent, 
	ShipmentStageType.actualPickupTransportEvent, 
	ShipmentStageType.deliveryTransportEvent, 
	ShipmentStageType.receiptTransportEvent, 
	ShipmentStageType.storageTransportEvent, 
	ShipmentStageType.acceptanceTransportEvent, 
	ShipmentStageType.terminalOperatorParty, 
	ShipmentStageType.customsAgentParty, SignatureType-1.iD, 
	SignatureType-1.note-list.note, SignatureType-1.validationDate, 
	SignatureType-1.validationTime, SignatureType-1.validatorID, 
	SignatureType-1.canonicalizationMethod, 
	SignatureType-1.signatureMethod, SignatureType-1.signatoryParty, 
	SignatureType-1.digitalSignatureAttachment, 
	SignatureType-1.originalDocumentReference, StatementLineType.iD, 
	StatementLineType.note-list.note, StatementLineType.uUID, 
	StatementLineType.balanceBroughtForwardIndicator, 
	StatementLineType.debitLineAmount, StatementLineType.creditLineAmount,
	StatementLineType.balanceAmount, StatementLineType.paymentPurposeCode,
	StatementLineType.paymentMeans, 
	StatementLineType.paymentTerms-list.paymentTerms, 
	StatementLineType.buyerCustomerParty, 
	StatementLineType.sellerSupplierParty, 
	StatementLineType.originatorCustomerParty, 
	StatementLineType.accountingCustomerParty, 
	StatementLineType.accountingSupplierParty, 
	StatementLineType.payeeParty, 
	StatementLineType.invoicePeriod-list.invoicePeriod, 
	StatementLineType.billingReference-list.billingReference, 
	StatementLineType.documentReference-list.documentReference, 
	StatementLineType.exchangeRate, 
	StatementLineType.allowanceCharge-list.allowanceCharge, 
	StatusType.conditionCode, StatusType.referenceDate, 
	StatusType.referenceTime, StatusType.description-list.description, 
	StatusType.statusReasonCode, 
	StatusType.statusReason-list.statusReason, StatusType.sequenceID, 
	StatusType.text-list.text, StatusType.indicationIndicator, 
	StatusType.percent, 
	StatusType.conditionValueMeasure-list.conditionValueMeasure, 
	StatusType.reliabilityPercent, StockAvailabilityReportLineType.iD, 
	StockAvailabilityReportLineType.note-list.note, 
	StockAvailabilityReportLineType.quantity, 
	StockAvailabilityReportLineType.valueAmount, 
	StockAvailabilityReportLineType.availabilityDate, 
	StockAvailabilityReportLineType.availabilityStatusCode, 
	StockAvailabilityReportLineType.item, StowageType.locationID, 
	StowageType.location-list.location, 
	StowageType.measurementDimension-list.measurementDimension, 
	SubcontractTermsType.rate, SubcontractTermsType.unknownPriceIndicator,
	SubcontractTermsType.description-list.description, 
	SubcontractTermsType.amount, SubscriberConsumptionType.consumptionID, 
	SubscriberConsumptionType.specificationTypeCode, 
	SubscriberConsumptionType.note-list.note, 
	SubscriberConsumptionType.totalMeteredQuantity, 
	SubscriberConsumptionType.subscriberParty, 
	SubscriberConsumptionType.utilityConsumptionPoint, 
	SubscriberConsumptionType.onAccountPayment-list.onAccountPayment, 
	SubscriberConsumptionType.consumption, 
	SubscriberConsumptionType.supplierConsumption-list.supplierConsumption,
	SupplierConsumptionType.description, 
	SupplierConsumptionType.utilitySupplierParty, 
	SupplierConsumptionType.utilityCustomerParty, 
	SupplierConsumptionType.consumption, 
	SupplierConsumptionType.consumptionLine-list.consumptionLine, 
	SupplierPartyType.customerAssignedAccountID, 
	SupplierPartyType.additionalAccountID-list.additionalAccountID, 
	SupplierPartyType.dataSendingCapability, SupplierPartyType.party, 
	SupplierPartyType.despatchContact, 
	SupplierPartyType.accountingContact, SupplierPartyType.sellerContact, 
	TaxCategoryType.iD, TaxCategoryType.name, TaxCategoryType.percent, 
	TaxCategoryType.baseUnitMeasure, TaxCategoryType.perUnitAmount, 
	TaxCategoryType.taxExemptionReasonCode, 
	TaxCategoryType.taxExemptionReason, TaxCategoryType.tierRange, 
	TaxCategoryType.tierRatePercent, TaxCategoryType.taxScheme, 
	TaxSchemeType.iD, TaxSchemeType.name, TaxSchemeType.taxTypeCode, 
	TaxSchemeType.currencyCode, 
	TaxSchemeType.jurisdictionRegionAddress-list.jurisdictionRegionAddress,
	TaxSubtotalType.taxableAmount, TaxSubtotalType.taxAmount, 
	TaxSubtotalType.calculationSequenceNumeric, 
	TaxSubtotalType.transactionCurrencyTaxAmount, TaxSubtotalType.percent,
	TaxSubtotalType.baseUnitMeasure, TaxSubtotalType.perUnitAmount, 
	TaxSubtotalType.tierRange, TaxSubtotalType.tierRatePercent, 
	TaxSubtotalType.taxCategory, TaxTotalType.taxAmount, 
	TaxTotalType.roundingAmount, TaxTotalType.taxEvidenceIndicator, 
	TaxTotalType.taxIncludedIndicator, 
	TaxTotalType.taxSubtotal-list.taxSubtotal, 
	TelecommunicationsServiceType.iD, 
	TelecommunicationsServiceType.callDate, 
	TelecommunicationsServiceType.callTime, 
	TelecommunicationsServiceType.serviceNumberCalled, 
	TelecommunicationsServiceType.telecommunicationsServiceCategory, 
	TelecommunicationsServiceType.telecommunicationsServiceCategoryCode, 
	TelecommunicationsServiceType.movieTitle, 
	TelecommunicationsServiceType.roamingPartnerName-list.roamingPartnerName,
	TelecommunicationsServiceType.payPerView, 
	TelecommunicationsServiceType.quantity, 
	TelecommunicationsServiceType.telecommunicationsServiceCall, 
	TelecommunicationsServiceType.telecommunicationsServiceCallCode, 
	TelecommunicationsServiceType.callBaseAmount, 
	TelecommunicationsServiceType.callExtensionAmount, 
	TelecommunicationsServiceType.price, 
	TelecommunicationsServiceType.country, 
	TelecommunicationsServiceType.exchangeRate-list.exchangeRate, 
	TelecommunicationsServiceType.allowanceCharge-list.allowanceCharge, 
	TelecommunicationsServiceType.taxTotal-list.taxTotal, 
	TelecommunicationsServiceType.callDuty-list.callDuty, 
	TelecommunicationsServiceType.timeDuty-list.timeDuty, 
	TelecommunicationsSupplyType.telecommunicationsSupplyType, 
	TelecommunicationsSupplyType.telecommunicationsSupplyTypeCode, 
	TelecommunicationsSupplyType.privacyCode, 
	TelecommunicationsSupplyType.description, 
	TelecommunicationsSupplyType.totalAmount, 
	TelecommunicationsSupplyType.telecommunicationsSupplyLine-list.telecommunicationsSupplyLine,
	TelecommunicationsSupplyLineType.iD, 
	TelecommunicationsSupplyLineType.phoneNumber, 
	TelecommunicationsSupplyLineType.description, 
	TelecommunicationsSupplyLineType.lineExtensionAmount, 
	TelecommunicationsSupplyLineType.exchangeRate-list.exchangeRate, 
	TelecommunicationsSupplyLineType.allowanceCharge-list.allowanceCharge,
	TelecommunicationsSupplyLineType.taxTotal-list.taxTotal, 
	TelecommunicationsSupplyLineType.telecommunicationsService-list.telecommunicationsService,
	TemperatureType.attributeID, TemperatureType.measure, 
	TemperatureType.description-list.description, TenderLineType.iD, 
	TenderLineType.note-list.note, TenderLineType.quantity, 
	TenderLineType.lineExtensionAmount, TenderLineType.totalTaxAmount, 
	TenderLineType.orderableUnit-list.orderableUnit, 
	TenderLineType.contentUnitQuantity, 
	TenderLineType.orderQuantityIncrementNumeric, 
	TenderLineType.minimumOrderQuantity, 
	TenderLineType.maximumOrderQuantity, 
	TenderLineType.warrantyInformation-list.warrantyInformation, 
	TenderLineType.packLevelCode, 
	TenderLineType.documentReference-list.documentReference, 
	TenderLineType.item, TenderLineType.offeredItemLocationQuantity-list.offeredItemLocationQuantity,
	TenderLineType.replacementRelatedItem-list.replacementRelatedItem, 
	TenderLineType.warrantyParty, TenderLineType.warrantyValidityPeriod, 
	TenderLineType.subTenderLine-list.subTenderLine, 
	TenderPreparationType.tenderEnvelopeID, 
	TenderPreparationType.tenderEnvelopeTypeCode, 
	TenderPreparationType.description-list.description, 
	TenderPreparationType.openTenderID, 
	TenderPreparationType.procurementProjectLotID-list.procurementProjectLotID,
	TenderPreparationType.documentTenderRequirement-list.documentTenderRequirement,
	TenderRequirementType.name-list.name, 
	TenderRequirementType.description-list.description, 
	TenderRequirementType.templateDocumentReference, 
	TenderResultType.tenderResultCode, 
	TenderResultType.description-list.description, 
	TenderResultType.advertisementAmount, TenderResultType.awardDate, 
	TenderResultType.awardTime, TenderResultType.receivedTenderQuantity, 
	TenderResultType.lowerTenderAmount, 
	TenderResultType.higherTenderAmount, TenderResultType.startDate, 
	TenderResultType.contract, TenderResultType.winningParty, 
	TenderResultType.awardedTenderedProject, 
	TenderResultType.contractFormalizationPeriod, 
	TenderResultType.subcontractTerms-list.subcontractTerms, 
	TenderedProjectType.procurementProjectLotID, 
	TenderedProjectType.variantID, TenderedProjectType.feeAmount, 
	TenderedProjectType.feeDescription-list.feeDescription, 
	TenderedProjectType.taxTotal-list.taxTotal, 
	TenderedProjectType.legalMonetaryTotal, 
	TenderedProjectType.tenderLine-list.tenderLine, 
	TenderedProjectType.awardingCriteriaResponse-list.awardingCriteriaResponse,
	TendererPartyQualificationType.interestedProcurementLotsID-list.interestedProcurementLotsID,
	TendererPartyQualificationType.mainQualifyingParty, 
	TendererPartyQualificationType.additionalQualifyingParty-list.additionalQualifyingParty,
	TendererQualificationRequestType.legalForm-list.legalForm, 
	TendererQualificationRequestType.personalSituation-list.personalSituation,
	TendererQualificationRequestType.operatingYearsQuantity, 
	TendererQualificationRequestType.employeeQuantity, 
	TendererQualificationRequestType.description-list.description, 
	TendererQualificationRequestType.requiredBusinessClassificationScheme-list.requiredBusinessClassificationScheme,
	TendererQualificationRequestType.technicalEvaluationCriteria-list.technicalEvaluationCriteria,
	TendererQualificationRequestType.financialEvaluationCriteria-list.financialEvaluationCriteria,
	TendererQualificationRequestType.specificTendererRequirement-list.specificTendererRequirement,
	TendererRequirementType.name-list.name, 
	TendererRequirementType.tendererRequirementTypeCode, 
	TendererRequirementType.description-list.description, 
	TendererRequirementType.suggestedEvidence-list.suggestedEvidence, 
	TenderingProcessType.iD, 
	TenderingProcessType.originalContractingSystemID, 
	TenderingProcessType.description-list.description, 
	TenderingProcessType.negotiationDescription-list.negotiationDescription,
	TenderingProcessType.procedureCode, TenderingProcessType.urgencyCode, 
	TenderingProcessType.expenseCode, 
	TenderingProcessType.partPresentationCode, 
	TenderingProcessType.contractingSystemCode, 
	TenderingProcessType.submissionMethodCode, 
	TenderingProcessType.candidateReductionConstraintIndicator, 
	TenderingProcessType.governmentAgreementConstraintIndicator, 
	TenderingProcessType.documentAvailabilityPeriod, 
	TenderingProcessType.tenderSubmissionDeadlinePeriod, 
	TenderingProcessType.invitationSubmissionPeriod, 
	TenderingProcessType.participationRequestReceptionPeriod, 
	TenderingProcessType.noticeDocumentReference-list.noticeDocumentReference,
	TenderingProcessType.additionalDocumentReference-list.additionalDocumentReference,
	TenderingProcessType.processJustification-list.processJustification, 
	TenderingProcessType.economicOperatorShortList, 
	TenderingProcessType.openTenderEvent-list.openTenderEvent, 
	TenderingProcessType.auctionTerms, 
	TenderingProcessType.frameworkAgreement, 
	TenderingTermsType.awardingMethodTypeCode, 
	TenderingTermsType.priceEvaluationCode, 
	TenderingTermsType.maximumVariantQuantity, 
	TenderingTermsType.variantConstraintIndicator, 
	TenderingTermsType.acceptedVariantsDescription-list.acceptedVariantsDescription,
	TenderingTermsType.priceRevisionFormulaDescription-list.priceRevisionFormulaDescription,
	TenderingTermsType.fundingProgramCode, 
	TenderingTermsType.fundingProgram-list.fundingProgram, 
	TenderingTermsType.maximumAdvertisementAmount, 
	TenderingTermsType.note-list.note, 
	TenderingTermsType.paymentFrequencyCode, 
	TenderingTermsType.economicOperatorRegistryURI, 
	TenderingTermsType.penaltyClauses-list.penaltyClauses, 
	TenderingTermsType.requiredCurriculaIndicator, 
	TenderingTermsType.requiredFinancialGuarantee-list.requiredFinancialGuarantee,
	TenderingTermsType.procurementLegislationDocumentReference, 
	TenderingTermsType.fiscalLegislationDocumentReference, 
	TenderingTermsType.environmentalLegislationDocumentReference, 
	TenderingTermsType.employmentLegislationDocumentReference, 
	TenderingTermsType.contractualDocumentReference-list.contractualDocumentReference,
	TenderingTermsType.callForTenderDocumentReference, 
	TenderingTermsType.warrantyValidityPeriod, 
	TenderingTermsType.paymentTerms-list.paymentTerms, 
	TenderingTermsType.tendererQualificationRequest, 
	TenderingTermsType.allowedSubcontractTerms-list.allowedSubcontractTerms,
	TenderingTermsType.tenderPreparation-list.tenderPreparation, 
	TenderingTermsType.contractExecutionRequirement-list.contractExecutionRequirement,
	TenderingTermsType.awardingTerms, 
	TenderingTermsType.additionalInformationParty, 
	TenderingTermsType.documentProviderParty, 
	TenderingTermsType.tenderRecipientParty, 
	TenderingTermsType.contractResponsibleParty, 
	TenderingTermsType.tenderEvaluationParty-list.tenderEvaluationParty, 
	TenderingTermsType.tenderValidityPeriod, 
	TenderingTermsType.contractAcceptancePeriod, 
	TenderingTermsType.appealTerms, 
	TenderingTermsType.language-list.language, 
	TenderingTermsType.budgetAccountLine-list.budgetAccountLine, 
	TradeFinancingType.iD, TradeFinancingType.financingInstrumentCode, 
	TradeFinancingType.clauseCode-list.clauseCode, 
	TradeFinancingType.clause-list.clause, 
	TradeFinancingType.contractDocumentReference, 
	TradeFinancingType.documentReference-list.documentReference, 
	TradeFinancingType.financingParty, 
	TradeFinancingType.financingFinancialAccount, 
	TradingTermsType.information-list.information, 
	TradingTermsType.reference, TradingTermsType.applicableAddress, 
	TransactionConditionsType.iD, TransactionConditionsType.actionCode, 
	TransactionConditionsType.description-list.description, 
	TransactionConditionsType.documentReference-list.documentReference, 
	TransportEquipmentType.iD, 
	TransportEquipmentType.referencedConsignmentID, 
	TransportEquipmentType.transportEquipmentTypeCode, 
	TransportEquipmentType.providerTypeCode, 
	TransportEquipmentType.ownerTypeCode, 
	TransportEquipmentType.sizeTypeCode, 
	TransportEquipmentType.dispositionCode, 
	TransportEquipmentType.fullnessIndicationCode, 
	TransportEquipmentType.refrigerationOnIndicator, 
	TransportEquipmentType.information, 
	TransportEquipmentType.returnabilityIndicator, 
	TransportEquipmentType.legalStatusIndicator, 
	TransportEquipmentType.airFlowPercent, 
	TransportEquipmentType.humidityPercent, 
	TransportEquipmentType.animalFoodApprovedIndicator, 
	TransportEquipmentType.humanFoodApprovedIndicator, 
	TransportEquipmentType.dangerousGoodsApprovedIndicator, 
	TransportEquipmentType.refrigeratedIndicator, 
	TransportEquipmentType.characteristics, 
	TransportEquipmentType.damageRemarks, 
	TransportEquipmentType.description, 
	TransportEquipmentType.specialTransportRequirments, 
	TransportEquipmentType.grossWeightMeasure, 
	TransportEquipmentType.grossVolumeMeasure, 
	TransportEquipmentType.tareWeightMeasure, 
	TransportEquipmentType.trackingDeviceCode, 
	TransportEquipmentType.powerIndicator, TransportEquipmentType.traceID,
	TransportEquipmentType.measurementDimension-list.measurementDimension,
	TransportEquipmentType.transportEquipmentSeal-list.transportEquipmentSeal,
	TransportEquipmentType.minimumTemperature, 
	TransportEquipmentType.maximumTemperature, 
	TransportEquipmentType.providerParty, 
	TransportEquipmentType.loadingProofParty, 
	TransportEquipmentType.supplierParty, 
	TransportEquipmentType.ownerParty, 
	TransportEquipmentType.operatingParty, 
	TransportEquipmentType.loadingLocation, 
	TransportEquipmentType.unloadingLocation, 
	TransportEquipmentType.storageLocation, 
	TransportEquipmentType.positioningTransportEvent-list.positioningTransportEvent,
	TransportEquipmentType.quarantineTransportEvent-list.quarantineTransportEvent,
	TransportEquipmentType.deliveryTransportEvent-list.deliveryTransportEvent,
	TransportEquipmentType.pickupTransportEvent-list.pickupTransportEvent,
	TransportEquipmentType.handlingTransportEvent-list.handlingTransportEvent,
	TransportEquipmentType.loadingTransportEvent-list.loadingTransportEvent,
	TransportEquipmentType.transportEvent-list.transportEvent, 
	TransportEquipmentType.applicableTransportMeans, 
	TransportEquipmentType.haulageTradingTerms-list.haulageTradingTerms, 
	TransportEquipmentType.hazardousGoodsTransit-list.hazardousGoodsTransit,
	TransportEquipmentType.packagedTransportHandlingUnit-list.packagedTransportHandlingUnit,
	TransportEquipmentType.serviceAllowanceCharge-list.serviceAllowanceCharge,
	TransportEquipmentType.freightAllowanceCharge-list.freightAllowanceCharge,
	TransportEquipmentType.attachedTransportEquipment-list.attachedTransportEquipment,
	TransportEquipmentType.goodsItem-list.goodsItem, 
	TransportEquipmentType.delivery, 
	TransportEquipmentType.containedInTransportEquipment-list.containedInTransportEquipment,
	TransportEquipmentType.pickup, TransportEquipmentType.despatch, 
	TransportEquipmentType.shipmentDocumentReference, 
	TransportEquipmentSealType.iD, 
	TransportEquipmentSealType.sealIssuerTypeCode, 
	TransportEquipmentSealType.condition, 
	TransportEquipmentSealType.sealStatusCode, 
	TransportEquipmentSealType.sealingPartyType, 
	TransportEventType.identificationID, 
	TransportEventType.occurrenceDate, TransportEventType.occurrenceTime, 
	TransportEventType.transportEventTypeCode, 
	TransportEventType.description, 
	TransportEventType.completionIndicator, 
	TransportEventType.reportedShipment, 
	TransportEventType.currentStatus-list.currentStatus, 
	TransportEventType.contact-list.contact, TransportEventType.location, 
	TransportExecutionTermsType.transportUserSpecialTerms-list.transportUserSpecialTerms,
	TransportExecutionTermsType.transportServiceProviderSpecialTerms-list.transportServiceProviderSpecialTerms,
	TransportExecutionTermsType.changeConditions-list.changeConditions, 
	TransportExecutionTermsType.paymentTerms, 
	TransportExecutionTermsType.deliveryTerms-list.deliveryTerms, 
	TransportExecutionTermsType.bonusPaymentTerms, 
	TransportExecutionTermsType.commissionPaymentTerms, 
	TransportExecutionTermsType.penaltyPaymentTerms, 
	TransportExecutionTermsType.environmentalEmission-list.environmentalEmission,
	TransportExecutionTermsType.notificationRequirement-list.notificationRequirement,
	TransportHandlingUnitType.iD, 
	TransportHandlingUnitType.transportHandlingUnitTypeCode, 
	TransportHandlingUnitType.handlingCode, 
	TransportHandlingUnitType.handlingInstructions, 
	TransportHandlingUnitType.hazardousRiskIndicator, 
	TransportHandlingUnitType.totalGoodsItemQuantity, 
	TransportHandlingUnitType.totalPackageQuantity, 
	TransportHandlingUnitType.damageRemarks-list.damageRemarks, 
	TransportHandlingUnitType.shippingMarks-list.shippingMarks, 
	TransportHandlingUnitType.handlingUnitDespatchLine-list.handlingUnitDespatchLine,
	TransportHandlingUnitType.actualPackage-list.actualPackage, 
	TransportHandlingUnitType.receivedHandlingUnitReceiptLine-list.receivedHandlingUnitReceiptLine,
	TransportHandlingUnitType.transportEquipment-list.transportEquipment, 
	TransportHandlingUnitType.transportMeans-list.transportMeans, 
	TransportHandlingUnitType.hazardousGoodsTransit-list.hazardousGoodsTransit,
	TransportHandlingUnitType.measurementDimension-list.measurementDimension,
	TransportHandlingUnitType.minimumTemperature, 
	TransportHandlingUnitType.maximumTemperature, 
	TransportHandlingUnitType.goodsItem-list.goodsItem, 
	TransportHandlingUnitType.floorSpaceMeasurementDimension, 
	TransportHandlingUnitType.palletSpaceMeasurementDimension, 
	TransportHandlingUnitType.shipmentDocumentReference-list.shipmentDocumentReference,
	TransportHandlingUnitType.status-list.status, 
	TransportLocationType.plannedDeparturePeriod, 
	TransportLocationType.plannedArrivalPeriod, 
	TransportLocationType.estimatedDeparturePeriod, 
	TransportLocationType.estimatedArrivalPeriod, 
	TransportLocationType.actualDepartureTransportEvent, 
	TransportLocationType.transportEvent, TransportLocationType.location, 
	TransportMeansType.journeyID, 
	TransportMeansType.registrationNationalityID, 
	TransportMeansType.registrationNationality-list.registrationNationality,
	TransportMeansType.directionCode, 
	TransportMeansType.transportMeansTypeCode, 
	TransportMeansType.tradeServiceCode, TransportMeansType.stowage, 
	TransportMeansType.airTransport, TransportMeansType.roadTransport, 
	TransportMeansType.railTransport, 
	TransportMeansType.maritimeTransport, TransportMeansType.ownerParty, 
	TransportMeansType.operatorParty-list.operatorParty, 
	TransportScheduleType.sequenceNumberID, 
	TransportScheduleType.referenceDate, 
	TransportScheduleType.referenceTime, 
	TransportScheduleType.reliabilityPercent, 
	TransportScheduleType.remarks-list.remarks, 
	TransportScheduleType.statusLocation, 
	TransportScheduleType.estimatedArrivalPeriod, 
	TransportScheduleType.estimatedDeparturePeriod, 
	TransportScheduleType.actualArrivalTransportEvent, 
	TransportScheduleType.actualDepartureTransportEvent, 
	TransportStatusType.timeDeviationIndicator, 
	TransportStatusType.conditionDeviationIndicator, 
	TransportStatusType.updatedDelivery, 
	TransportStatusType.updatedDespatch, 
	TransportStatusType.statusLocation, 
	TransportStatusType.referencedTransportHandlingUnit-list.referencedTransportHandlingUnit,
	TransportationSegmentType.sequenceNumberID, 
	TransportationSegmentType.transportExecutionPlanReferenceID, 
	TransportationSegmentType.transportModeCode, 
	TransportationSegmentType.transportMeansTypeCode, 
	TransportationSegmentType.transportationService, 
	TransportationSegmentType.transportServiceProviderParty, 
	TransportationSegmentType.carryingTransportEquipment, 
	TransportationSegmentType.carryingPackage, 
	TransportationSegmentType.carryingTransportMeans, 
	TransportationSegmentType.departureTransportLocation, 
	TransportationSegmentType.intermediateTransportLocation-list.intermediateTransportLocation,
	TransportationSegmentType.arrivalTransportLocation, 
	TransportationServiceType.transportServiceCode, 
	TransportationServiceType.tariffClassCode, 
	TransportationServiceType.priority, 
	TransportationServiceType.freightRateClassCode, 
	TransportationServiceType.transportationServiceDescription, 
	TransportationServiceType.transportationServiceDetailsURI, 
	TransportationServiceType.nominationDate, 
	TransportationServiceType.nominationTime, 
	UnstructuredPriceType.priceAmount, UnstructuredPriceType.timeAmount, 
	UtilityItemType.iD, UtilityItemType.subscriberID, 
	UtilityItemType.subscriberIDType, 
	UtilityItemType.subscriberIDTypeCode, 
	UtilityItemType.description-list.description, 
	UtilityItemType.packQuantity, UtilityItemType.packSizeNumeric, 
	UtilityItemType.consumptionType, UtilityItemType.consumptionTypeCode, 
	UtilityItemType.currentChargeType, 
	UtilityItemType.currentChargeTypeCode, 
	UtilityItemType.oneTimeChargeType, 
	UtilityItemType.oneTimeChargeTypeCode, UtilityItemType.taxCategory, 
	UtilityItemType.contract, WebSiteAccessType.uRI, 
	WebSiteAccessType.password, WebSiteAccessType.login AS CAPITALIZED
    NAME SignatureType-1 AS "SignatureType"
    UNTAGGED SEQUENCE OF
END
