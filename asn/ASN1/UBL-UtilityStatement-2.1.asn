UtilityStatement-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, UtilityStatementTypeCode, Note,
    DocumentCurrencyCode, AccountingCostCode, AccountingCost
    FROM CommonBasicComponents-2
    ParentDocumentReference, AdditionalDocumentReference, Signature-1, 
    SenderParty, ReceiverParty, BuyerCustomerParty, SubscriberParty, 
    MainOnAccountPayment, SubscriberConsumption
    FROM CommonAggregateComponents-2;

UtilityStatement ::= UtilityStatementType

UtilityStatementType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    utilityStatementTypeCode UtilityStatementTypeCode,
    note-list  SEQUENCE OF note Note,
    documentCurrencyCode DocumentCurrencyCode,
    accountingCostCode AccountingCostCode OPTIONAL,
    accountingCost AccountingCost OPTIONAL,
    parentDocumentReference ParentDocumentReference,
    additionalDocumentReference-list SEQUENCE OF additionalDocumentReference 
	AdditionalDocumentReference,
    signature-list SEQUENCE OF signature Signature-1,
    senderParty SenderParty,
    receiverParty ReceiverParty,
    buyerCustomerParty BuyerCustomerParty OPTIONAL,
    subscriberParty SubscriberParty OPTIONAL,
    mainOnAccountPayment-list SEQUENCE OF mainOnAccountPayment 
	MainOnAccountPayment,
    subscriberConsumption-list SEQUENCE OF subscriberConsumption 
	SubscriberConsumption
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:UtilityStatement-2"
	PREFIX "ns60"
    NAMESPACE UtilityStatementType.uBLExtensions
	AS "urn:oasis:names:specification:ubl:schema:xsd:CommonExtensionComponents-2"
	    PREFIX "ext"
    NAMESPACE UtilityStatementType.uBLVersionID, 
	UtilityStatementType.customizationID, UtilityStatementType.profileID, 
	UtilityStatementType.profileExecutionID, UtilityStatementType.iD, 
	UtilityStatementType.copyIndicator, UtilityStatementType.uUID, 
	UtilityStatementType.issueDate, UtilityStatementType.issueTime, 
	UtilityStatementType.utilityStatementTypeCode, 
	UtilityStatementType.note-list.note, 
	UtilityStatementType.documentCurrencyCode, 
	UtilityStatementType.accountingCostCode, 
	UtilityStatementType.accountingCost
	AS "urn:oasis:names:specification:ubl:schema:xsd:CommonBasicComponents-2"
	    PREFIX "cbc"
    NAMESPACE UtilityStatementType.parentDocumentReference, 
	UtilityStatementType.additionalDocumentReference-list.additionalDocumentReference,
	UtilityStatementType.signature-list.signature, 
	UtilityStatementType.senderParty, UtilityStatementType.receiverParty, 
	UtilityStatementType.buyerCustomerParty, 
	UtilityStatementType.subscriberParty, 
	UtilityStatementType.mainOnAccountPayment-list.mainOnAccountPayment, 
	UtilityStatementType.subscriberConsumption-list.subscriberConsumption
	AS "urn:oasis:names:specification:ubl:schema:xsd:CommonAggregateComponents-2"
	    PREFIX "cac"
    NAME UtilityStatementType.uBLExtensions, 
	UtilityStatementType.uBLVersionID, 
	UtilityStatementType.customizationID, UtilityStatementType.profileID, 
	UtilityStatementType.profileExecutionID, UtilityStatementType.iD, 
	UtilityStatementType.copyIndicator, UtilityStatementType.uUID, 
	UtilityStatementType.issueDate, UtilityStatementType.issueTime, 
	UtilityStatementType.utilityStatementTypeCode, 
	UtilityStatementType.note-list.note, 
	UtilityStatementType.documentCurrencyCode, 
	UtilityStatementType.accountingCostCode, 
	UtilityStatementType.accountingCost, 
	UtilityStatementType.parentDocumentReference, 
	UtilityStatementType.additionalDocumentReference-list.additionalDocumentReference,
	UtilityStatementType.signature-list.signature, 
	UtilityStatementType.senderParty, UtilityStatementType.receiverParty, 
	UtilityStatementType.buyerCustomerParty, 
	UtilityStatementType.subscriberParty, 
	UtilityStatementType.mainOnAccountPayment-list.mainOnAccountPayment, 
	UtilityStatementType.subscriberConsumption-list.subscriberConsumption
	AS CAPITALIZED
    UNTAGGED SEQUENCE OF
END
