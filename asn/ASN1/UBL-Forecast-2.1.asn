Forecast-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, VersionID, 
    BasedOnConsensusIndicator, ForecastPurposeCode
    FROM CommonBasicComponents-2
    ForecastPeriod, AdditionalDocumentReference, Signature-1, SenderParty, 
    ReceiverParty, BuyerCustomerParty, SellerSupplierParty, ForecastLine
    FROM CommonAggregateComponents-2;

Forecast ::= ForecastType

ForecastType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    versionID  VersionID OPTIONAL,
    basedOnConsensusIndicator BasedOnConsensusIndicator OPTIONAL,
    forecastPurposeCode ForecastPurposeCode,
    forecastPeriod ForecastPeriod,
    additionalDocumentReference-list SEQUENCE OF additionalDocumentReference 
	AdditionalDocumentReference,
    signature-list SEQUENCE OF signature Signature-1,
    senderParty SenderParty,
    receiverParty ReceiverParty,
    buyerCustomerParty BuyerCustomerParty OPTIONAL,
    sellerSupplierParty SellerSupplierParty OPTIONAL,
    forecastLine-list SEQUENCE (SIZE(1..MAX)) OF forecastLine ForecastLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:Forecast-2"
	PREFIX "ns20"
    NAMESPACE ForecastType.uBLExtensions
	AS "urn:oasis:names:specification:ubl:schema:xsd:CommonExtensionComponents-2"
	    PREFIX "ext"
    NAMESPACE ForecastType.uBLVersionID, ForecastType.customizationID, 
	ForecastType.profileID, ForecastType.profileExecutionID, 
	ForecastType.iD, ForecastType.copyIndicator, ForecastType.uUID, 
	ForecastType.issueDate, ForecastType.issueTime, 
	ForecastType.note-list.note, ForecastType.versionID, 
	ForecastType.basedOnConsensusIndicator, 
	ForecastType.forecastPurposeCode
	AS "urn:oasis:names:specification:ubl:schema:xsd:CommonBasicComponents-2"
	    PREFIX "cbc"
    NAMESPACE ForecastType.forecastPeriod, 
	ForecastType.additionalDocumentReference-list.additionalDocumentReference,
	ForecastType.signature-list.signature, ForecastType.senderParty, 
	ForecastType.receiverParty, ForecastType.buyerCustomerParty, 
	ForecastType.sellerSupplierParty, 
	ForecastType.forecastLine-list.forecastLine
	AS "urn:oasis:names:specification:ubl:schema:xsd:CommonAggregateComponents-2"
	    PREFIX "cac"
    NAME ForecastType.uBLExtensions, ForecastType.uBLVersionID, 
	ForecastType.customizationID, ForecastType.profileID, 
	ForecastType.profileExecutionID, ForecastType.iD, 
	ForecastType.copyIndicator, ForecastType.uUID, ForecastType.issueDate,
	ForecastType.issueTime, ForecastType.note-list.note, 
	ForecastType.versionID, ForecastType.basedOnConsensusIndicator, 
	ForecastType.forecastPurposeCode, ForecastType.forecastPeriod, 
	ForecastType.additionalDocumentReference-list.additionalDocumentReference,
	ForecastType.signature-list.signature, ForecastType.senderParty, 
	ForecastType.receiverParty, ForecastType.buyerCustomerParty, 
	ForecastType.sellerSupplierParty, 
	ForecastType.forecastLine-list.forecastLine AS CAPITALIZED
    UNTAGGED SEQUENCE OF
END
