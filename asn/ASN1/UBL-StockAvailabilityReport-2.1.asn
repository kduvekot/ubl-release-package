StockAvailabilityReport-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, DocumentCurrencyCode
    FROM CommonBasicComponents-2
    InventoryPeriod, DocumentReference, Signature-1, SellerSupplierParty, 
    RetailerCustomerParty, InventoryReportingParty, 
    StockAvailabilityReportLine
    FROM CommonAggregateComponents-2;

StockAvailabilityReport ::= StockAvailabilityReportType

StockAvailabilityReportType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    documentCurrencyCode DocumentCurrencyCode OPTIONAL,
    inventoryPeriod InventoryPeriod OPTIONAL,
    documentReference-list SEQUENCE OF documentReference DocumentReference,
    signature-list SEQUENCE OF signature Signature-1,
    sellerSupplierParty SellerSupplierParty,
    retailerCustomerParty RetailerCustomerParty OPTIONAL,
    inventoryReportingParty InventoryReportingParty,
    stockAvailabilityReportLine-list SEQUENCE (SIZE(1..MAX)) OF 
	stockAvailabilityReportLine StockAvailabilityReportLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:StockAvailabilityReport-2"
	PREFIX "ns48"
    NAMESPACE StockAvailabilityReportType.uBLExtensions
	AS "urn:oasis:names:specification:ubl:schema:xsd:CommonExtensionComponents-2"
	    PREFIX "ext"
    NAMESPACE StockAvailabilityReportType.uBLVersionID, 
	StockAvailabilityReportType.customizationID, 
	StockAvailabilityReportType.profileID, 
	StockAvailabilityReportType.profileExecutionID, 
	StockAvailabilityReportType.iD, 
	StockAvailabilityReportType.copyIndicator, 
	StockAvailabilityReportType.uUID, 
	StockAvailabilityReportType.issueDate, 
	StockAvailabilityReportType.issueTime, 
	StockAvailabilityReportType.note-list.note, 
	StockAvailabilityReportType.documentCurrencyCode
	AS "urn:oasis:names:specification:ubl:schema:xsd:CommonBasicComponents-2"
	    PREFIX "cbc"
    NAMESPACE StockAvailabilityReportType.inventoryPeriod, 
	StockAvailabilityReportType.documentReference-list.documentReference, 
	StockAvailabilityReportType.signature-list.signature, 
	StockAvailabilityReportType.sellerSupplierParty, 
	StockAvailabilityReportType.retailerCustomerParty, 
	StockAvailabilityReportType.inventoryReportingParty, 
	StockAvailabilityReportType.stockAvailabilityReportLine-list.stockAvailabilityReportLine
	AS "urn:oasis:names:specification:ubl:schema:xsd:CommonAggregateComponents-2"
	    PREFIX "cac"
    NAME StockAvailabilityReportType.uBLExtensions, 
	StockAvailabilityReportType.uBLVersionID, 
	StockAvailabilityReportType.customizationID, 
	StockAvailabilityReportType.profileID, 
	StockAvailabilityReportType.profileExecutionID, 
	StockAvailabilityReportType.iD, 
	StockAvailabilityReportType.copyIndicator, 
	StockAvailabilityReportType.uUID, 
	StockAvailabilityReportType.issueDate, 
	StockAvailabilityReportType.issueTime, 
	StockAvailabilityReportType.note-list.note, 
	StockAvailabilityReportType.documentCurrencyCode, 
	StockAvailabilityReportType.inventoryPeriod, 
	StockAvailabilityReportType.documentReference-list.documentReference, 
	StockAvailabilityReportType.signature-list.signature, 
	StockAvailabilityReportType.sellerSupplierParty, 
	StockAvailabilityReportType.retailerCustomerParty, 
	StockAvailabilityReportType.inventoryReportingParty, 
	StockAvailabilityReportType.stockAvailabilityReportLine-list.stockAvailabilityReportLine
	AS CAPITALIZED
    UNTAGGED SEQUENCE OF
END
