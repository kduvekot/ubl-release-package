AttachedDocument-2
DEFINITIONS AUTOMATIC TAGS ::=
BEGIN
IMPORTS 
    UBLExtensions
    FROM CommonExtensionComponents-2
    UBLVersionID, CustomizationID, ProfileID, ProfileExecutionID, ID-1, UUID, 
    IssueDate, IssueTime, Note, DocumentTypeCode, DocumentType, 
    ParentDocumentID, ParentDocumentTypeCode, ParentDocumentVersionID
    FROM CommonBasicComponents-2
    Signature-1, SenderParty, ReceiverParty, Attachment, 
    ParentDocumentLineReference
    FROM CommonAggregateComponents-2;

AttachedDocument ::= AttachedDocumentType

AttachedDocumentType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    uUID       UUID OPTIONAL,
    issueDate  IssueDate,
    issueTime  IssueTime OPTIONAL,
    note-list  SEQUENCE OF note Note,
    documentTypeCode DocumentTypeCode OPTIONAL,
    documentType DocumentType OPTIONAL,
    parentDocumentID ParentDocumentID,
    parentDocumentTypeCode ParentDocumentTypeCode OPTIONAL,
    parentDocumentVersionID ParentDocumentVersionID OPTIONAL,
    signature-list SEQUENCE OF signature Signature-1,
    senderParty SenderParty,
    receiverParty ReceiverParty,
    attachment Attachment,
    parentDocumentLineReference-list SEQUENCE OF parentDocumentLineReference 
	ParentDocumentLineReference
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:AttachedDocument-2"
	PREFIX "ns1"
    NAMESPACE AttachedDocumentType.uBLExtensions
	AS "urn:oasis:names:specification:ubl:schema:xsd:CommonExtensionComponents-2"
	    PREFIX "ext"
    NAMESPACE AttachedDocumentType.uBLVersionID, 
	AttachedDocumentType.customizationID, AttachedDocumentType.profileID, 
	AttachedDocumentType.profileExecutionID, AttachedDocumentType.iD, 
	AttachedDocumentType.uUID, AttachedDocumentType.issueDate, 
	AttachedDocumentType.issueTime, AttachedDocumentType.note-list.note, 
	AttachedDocumentType.documentTypeCode, 
	AttachedDocumentType.documentType, 
	AttachedDocumentType.parentDocumentID, 
	AttachedDocumentType.parentDocumentTypeCode, 
	AttachedDocumentType.parentDocumentVersionID
	AS "urn:oasis:names:specification:ubl:schema:xsd:CommonBasicComponents-2"
	    PREFIX "cbc"
    NAMESPACE AttachedDocumentType.signature-list.signature, 
	AttachedDocumentType.senderParty, AttachedDocumentType.receiverParty, 
	AttachedDocumentType.attachment, 
	AttachedDocumentType.parentDocumentLineReference-list.parentDocumentLineReference
	AS "urn:oasis:names:specification:ubl:schema:xsd:CommonAggregateComponents-2"
	    PREFIX "cac"
    NAME AttachedDocumentType.uBLExtensions, 
	AttachedDocumentType.uBLVersionID, 
	AttachedDocumentType.customizationID, AttachedDocumentType.profileID, 
	AttachedDocumentType.profileExecutionID, AttachedDocumentType.iD, 
	AttachedDocumentType.uUID, AttachedDocumentType.issueDate, 
	AttachedDocumentType.issueTime, AttachedDocumentType.note-list.note, 
	AttachedDocumentType.documentTypeCode, 
	AttachedDocumentType.documentType, 
	AttachedDocumentType.parentDocumentID, 
	AttachedDocumentType.parentDocumentTypeCode, 
	AttachedDocumentType.parentDocumentVersionID, 
	AttachedDocumentType.signature-list.signature, 
	AttachedDocumentType.senderParty, AttachedDocumentType.receiverParty, 
	AttachedDocumentType.attachment, 
	AttachedDocumentType.parentDocumentLineReference-list.parentDocumentLineReference
	AS CAPITALIZED
    UNTAGGED SEQUENCE OF
END
