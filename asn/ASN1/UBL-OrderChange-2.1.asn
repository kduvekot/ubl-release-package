OrderChange-2
DEFINITIONS AUTOMATIC TAGS ::=
BEGIN
IMPORTS 
    UBLExtensions
    FROM CommonExtensionComponents-2
    UBLVersionID, CustomizationID, ProfileID, ProfileExecutionID, ID-1, 
    SalesOrderID, CopyIndicator, UUID, IssueDate, IssueTime, SequenceNumberID,
    Note, RequestedInvoiceCurrencyCode, DocumentCurrencyCode, 
    PricingCurrencyCode, TaxCurrencyCode, CustomerReference, 
    AccountingCostCode, AccountingCost, LineCountNumeric
    FROM CommonBasicComponents-2
    ValidityPeriod, OrderReference, QuotationDocumentReference, 
    OriginatorDocumentReference, AdditionalDocumentReference, Contract, 
    Signature-1, BuyerCustomerParty, SellerSupplierParty, 
    OriginatorCustomerParty, FreightForwarderParty, AccountingCustomerParty, 
    AccountingSupplierParty, Delivery, DeliveryTerms, PaymentMeans, 
    PaymentTerms, TransactionConditions, AllowanceCharge, TaxExchangeRate, 
    PricingExchangeRate, PaymentExchangeRate, DestinationCountry, TaxTotal, 
    AnticipatedMonetaryTotal, OrderLine
    FROM CommonAggregateComponents-2;

OrderChange ::= OrderChangeType

OrderChangeType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    salesOrderID SalesOrderID OPTIONAL,
    copyIndicator CopyIndicator OPTIONAL,
    uUID       UUID OPTIONAL,
    issueDate  IssueDate,
    issueTime  IssueTime OPTIONAL,
    sequenceNumberID SequenceNumberID,
    note-list  SEQUENCE OF note Note,
    requestedInvoiceCurrencyCode RequestedInvoiceCurrencyCode OPTIONAL,
    documentCurrencyCode DocumentCurrencyCode OPTIONAL,
    pricingCurrencyCode PricingCurrencyCode OPTIONAL,
    taxCurrencyCode TaxCurrencyCode OPTIONAL,
    customerReference CustomerReference OPTIONAL,
    accountingCostCode AccountingCostCode OPTIONAL,
    accountingCost AccountingCost OPTIONAL,
    lineCountNumeric LineCountNumeric OPTIONAL,
    validityPeriod-list SEQUENCE OF validityPeriod ValidityPeriod,
    orderReference OrderReference,
    quotationDocumentReference QuotationDocumentReference OPTIONAL,
    originatorDocumentReference OriginatorDocumentReference OPTIONAL,
    additionalDocumentReference-list SEQUENCE OF additionalDocumentReference 
	AdditionalDocumentReference,
    contract-list SEQUENCE OF contract Contract,
    signature-list SEQUENCE OF signature Signature-1,
    buyerCustomerParty BuyerCustomerParty,
    sellerSupplierParty SellerSupplierParty,
    originatorCustomerParty OriginatorCustomerParty OPTIONAL,
    freightForwarderParty FreightForwarderParty OPTIONAL,
    accountingCustomerParty AccountingCustomerParty OPTIONAL,
    accountingSupplierParty AccountingSupplierParty OPTIONAL,
    delivery-list SEQUENCE OF delivery Delivery,
    deliveryTerms DeliveryTerms OPTIONAL,
    paymentMeans-list SEQUENCE OF paymentMeans PaymentMeans,
    paymentTerms-list SEQUENCE OF paymentTerms PaymentTerms,
    transactionConditions TransactionConditions OPTIONAL,
    allowanceCharge-list SEQUENCE OF allowanceCharge AllowanceCharge,
    taxExchangeRate TaxExchangeRate OPTIONAL,
    pricingExchangeRate PricingExchangeRate OPTIONAL,
    paymentExchangeRate PaymentExchangeRate OPTIONAL,
    destinationCountry DestinationCountry OPTIONAL,
    taxTotal-list SEQUENCE OF taxTotal TaxTotal,
    anticipatedMonetaryTotal AnticipatedMonetaryTotal OPTIONAL,
    orderLine-list SEQUENCE (SIZE(1..MAX)) OF orderLine OrderLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:OrderChange-2"
	PREFIX "ns32"
    NAMESPACE OrderChangeType.uBLExtensions
	AS "urn:oasis:names:specification:ubl:schema:xsd:CommonExtensionComponents-2"
	    PREFIX "ext"
    NAMESPACE OrderChangeType.uBLVersionID, OrderChangeType.customizationID, 
	OrderChangeType.profileID, OrderChangeType.profileExecutionID, 
	OrderChangeType.iD, OrderChangeType.salesOrderID, 
	OrderChangeType.copyIndicator, OrderChangeType.uUID, 
	OrderChangeType.issueDate, OrderChangeType.issueTime, 
	OrderChangeType.sequenceNumberID, OrderChangeType.note-list.note, 
	OrderChangeType.requestedInvoiceCurrencyCode, 
	OrderChangeType.documentCurrencyCode, 
	OrderChangeType.pricingCurrencyCode, OrderChangeType.taxCurrencyCode, 
	OrderChangeType.customerReference, OrderChangeType.accountingCostCode,
	OrderChangeType.accountingCost, OrderChangeType.lineCountNumeric
	AS "urn:oasis:names:specification:ubl:schema:xsd:CommonBasicComponents-2"
	    PREFIX "cbc"
    NAMESPACE OrderChangeType.validityPeriod-list.validityPeriod, 
	OrderChangeType.orderReference, 
	OrderChangeType.quotationDocumentReference, 
	OrderChangeType.originatorDocumentReference, 
	OrderChangeType.additionalDocumentReference-list.additionalDocumentReference,
	OrderChangeType.contract-list.contract, 
	OrderChangeType.signature-list.signature, 
	OrderChangeType.buyerCustomerParty, 
	OrderChangeType.sellerSupplierParty, 
	OrderChangeType.originatorCustomerParty, 
	OrderChangeType.freightForwarderParty, 
	OrderChangeType.accountingCustomerParty, 
	OrderChangeType.accountingSupplierParty, 
	OrderChangeType.delivery-list.delivery, OrderChangeType.deliveryTerms,
	OrderChangeType.paymentMeans-list.paymentMeans, 
	OrderChangeType.paymentTerms-list.paymentTerms, 
	OrderChangeType.transactionConditions, 
	OrderChangeType.allowanceCharge-list.allowanceCharge, 
	OrderChangeType.taxExchangeRate, OrderChangeType.pricingExchangeRate, 
	OrderChangeType.paymentExchangeRate, 
	OrderChangeType.destinationCountry, 
	OrderChangeType.taxTotal-list.taxTotal, 
	OrderChangeType.anticipatedMonetaryTotal, 
	OrderChangeType.orderLine-list.orderLine
	AS "urn:oasis:names:specification:ubl:schema:xsd:CommonAggregateComponents-2"
	    PREFIX "cac"
    NAME OrderChangeType.uBLExtensions, OrderChangeType.uBLVersionID, 
	OrderChangeType.customizationID, OrderChangeType.profileID, 
	OrderChangeType.profileExecutionID, OrderChangeType.iD, 
	OrderChangeType.salesOrderID, OrderChangeType.copyIndicator, 
	OrderChangeType.uUID, OrderChangeType.issueDate, 
	OrderChangeType.issueTime, OrderChangeType.sequenceNumberID, 
	OrderChangeType.note-list.note, 
	OrderChangeType.requestedInvoiceCurrencyCode, 
	OrderChangeType.documentCurrencyCode, 
	OrderChangeType.pricingCurrencyCode, OrderChangeType.taxCurrencyCode, 
	OrderChangeType.customerReference, OrderChangeType.accountingCostCode,
	OrderChangeType.accountingCost, OrderChangeType.lineCountNumeric, 
	OrderChangeType.validityPeriod-list.validityPeriod, 
	OrderChangeType.orderReference, 
	OrderChangeType.quotationDocumentReference, 
	OrderChangeType.originatorDocumentReference, 
	OrderChangeType.additionalDocumentReference-list.additionalDocumentReference,
	OrderChangeType.contract-list.contract, 
	OrderChangeType.signature-list.signature, 
	OrderChangeType.buyerCustomerParty, 
	OrderChangeType.sellerSupplierParty, 
	OrderChangeType.originatorCustomerParty, 
	OrderChangeType.freightForwarderParty, 
	OrderChangeType.accountingCustomerParty, 
	OrderChangeType.accountingSupplierParty, 
	OrderChangeType.delivery-list.delivery, OrderChangeType.deliveryTerms,
	OrderChangeType.paymentMeans-list.paymentMeans, 
	OrderChangeType.paymentTerms-list.paymentTerms, 
	OrderChangeType.transactionConditions, 
	OrderChangeType.allowanceCharge-list.allowanceCharge, 
	OrderChangeType.taxExchangeRate, OrderChangeType.pricingExchangeRate, 
	OrderChangeType.paymentExchangeRate, 
	OrderChangeType.destinationCountry, 
	OrderChangeType.taxTotal-list.taxTotal, 
	OrderChangeType.anticipatedMonetaryTotal, 
	OrderChangeType.orderLine-list.orderLine AS CAPITALIZED
    UNTAGGED SEQUENCE OF
END
