CallForTenders-2
DEFINITIONS AUTOMATIC TAGS ::=
BEGIN
IMPORTS 
    UBLExtensions
    FROM CommonExtensionComponents-2
    UBLVersionID, CustomizationID, ProfileID, ProfileExecutionID, ID-1, 
    CopyIndicator, UUID, ContractFolderID, ApprovalDate, IssueDate, IssueTime,
    Note
    FROM CommonBasicComponents-2
    LegalDocumentReference, TechnicalDocumentReference, 
    AdditionalDocumentReference, Signature-1, ContractingParty, 
    OriginatorCustomerParty, ReceiverParty, TenderingTerms, TenderingProcess, 
    ProcurementProject, ProcurementProjectLot
    FROM CommonAggregateComponents-2;

CallForTenders ::= CallForTendersType

CallForTendersType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    contractFolderID ContractFolderID,
    approvalDate ApprovalDate OPTIONAL,
    issueDate  IssueDate,
    issueTime  IssueTime OPTIONAL,
    note-list  SEQUENCE OF note Note,
    legalDocumentReference LegalDocumentReference OPTIONAL,
    technicalDocumentReference TechnicalDocumentReference OPTIONAL,
    additionalDocumentReference-list SEQUENCE OF additionalDocumentReference 
	AdditionalDocumentReference,
    signature-list SEQUENCE OF signature Signature-1,
    contractingParty ContractingParty,
    originatorCustomerParty-list SEQUENCE OF originatorCustomerParty 
	OriginatorCustomerParty,
    receiverParty ReceiverParty OPTIONAL,
    tenderingTerms TenderingTerms OPTIONAL,
    tenderingProcess TenderingProcess OPTIONAL,
    procurementProject ProcurementProject,
    procurementProjectLot-list SEQUENCE OF procurementProjectLot 
	ProcurementProjectLot
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:CallForTenders-2"
	PREFIX "ns4"
    NAMESPACE CallForTendersType.uBLExtensions
	AS "urn:oasis:names:specification:ubl:schema:xsd:CommonExtensionComponents-2"
	    PREFIX "ext"
    NAMESPACE CallForTendersType.uBLVersionID, 
	CallForTendersType.customizationID, CallForTendersType.profileID, 
	CallForTendersType.profileExecutionID, CallForTendersType.iD, 
	CallForTendersType.copyIndicator, CallForTendersType.uUID, 
	CallForTendersType.contractFolderID, CallForTendersType.approvalDate, 
	CallForTendersType.issueDate, CallForTendersType.issueTime, 
	CallForTendersType.note-list.note
	AS "urn:oasis:names:specification:ubl:schema:xsd:CommonBasicComponents-2"
	    PREFIX "cbc"
    NAMESPACE CallForTendersType.legalDocumentReference, 
	CallForTendersType.technicalDocumentReference, 
	CallForTendersType.additionalDocumentReference-list.additionalDocumentReference,
	CallForTendersType.signature-list.signature, 
	CallForTendersType.contractingParty, 
	CallForTendersType.originatorCustomerParty-list.originatorCustomerParty,
	CallForTendersType.receiverParty, CallForTendersType.tenderingTerms, 
	CallForTendersType.tenderingProcess, 
	CallForTendersType.procurementProject, 
	CallForTendersType.procurementProjectLot-list.procurementProjectLot
	AS "urn:oasis:names:specification:ubl:schema:xsd:CommonAggregateComponents-2"
	    PREFIX "cac"
    NAME CallForTendersType.uBLExtensions, CallForTendersType.uBLVersionID, 
	CallForTendersType.customizationID, CallForTendersType.profileID, 
	CallForTendersType.profileExecutionID, CallForTendersType.iD, 
	CallForTendersType.copyIndicator, CallForTendersType.uUID, 
	CallForTendersType.contractFolderID, CallForTendersType.approvalDate, 
	CallForTendersType.issueDate, CallForTendersType.issueTime, 
	CallForTendersType.note-list.note, 
	CallForTendersType.legalDocumentReference, 
	CallForTendersType.technicalDocumentReference, 
	CallForTendersType.additionalDocumentReference-list.additionalDocumentReference,
	CallForTendersType.signature-list.signature, 
	CallForTendersType.contractingParty, 
	CallForTendersType.originatorCustomerParty-list.originatorCustomerParty,
	CallForTendersType.receiverParty, CallForTendersType.tenderingTerms, 
	CallForTendersType.tenderingProcess, 
	CallForTendersType.procurementProject, 
	CallForTendersType.procurementProjectLot-list.procurementProjectLot
	AS CAPITALIZED
    UNTAGGED SEQUENCE OF
END
