GuaranteeCertificate-2
DEFINITIONS AUTOMATIC TAGS ::=
BEGIN
IMPORTS 
    UBLExtensions
    FROM CommonExtensionComponents-2
    UBLVersionID, CustomizationID, ProfileID, ProfileExecutionID, ID-1, 
    CopyIndicator, UUID, ContractFolderID, IssueDate, IssueTime, 
    GuaranteeTypeCode, Purpose, LiabilityAmount, ConstitutionCode, Note
    FROM CommonBasicComponents-2
    ApplicablePeriod, ApplicableRegulation, GuaranteeDocumentReference, 
    ImmobilizedSecurity, Signature-1, GuarantorParty, InterestedParty, 
    BeneficiaryParty
    FROM CommonAggregateComponents-2;

GuaranteeCertificate ::= GuaranteeCertificateType

GuaranteeCertificateType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    contractFolderID ContractFolderID,
    issueDate  IssueDate,
    issueTime  IssueTime OPTIONAL,
    guaranteeTypeCode GuaranteeTypeCode OPTIONAL,
    purpose-list SEQUENCE OF purpose Purpose,
    liabilityAmount LiabilityAmount,
    constitutionCode ConstitutionCode OPTIONAL,
    note-list  SEQUENCE OF note Note,
    applicablePeriod ApplicablePeriod OPTIONAL,
    applicableRegulation-list SEQUENCE OF applicableRegulation 
	ApplicableRegulation,
    guaranteeDocumentReference-list SEQUENCE OF guaranteeDocumentReference 
	GuaranteeDocumentReference,
    immobilizedSecurity-list SEQUENCE OF immobilizedSecurity 
	ImmobilizedSecurity,
    signature-list SEQUENCE (SIZE(1..MAX)) OF signature Signature-1,
    guarantorParty GuarantorParty,
    interestedParty InterestedParty,
    beneficiaryParty BeneficiaryParty OPTIONAL
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:GuaranteeCertificate-2"
	PREFIX "ns25"
    NAMESPACE GuaranteeCertificateType.uBLExtensions
	AS "urn:oasis:names:specification:ubl:schema:xsd:CommonExtensionComponents-2"
	    PREFIX "ext"
    NAMESPACE GuaranteeCertificateType.uBLVersionID, 
	GuaranteeCertificateType.customizationID, 
	GuaranteeCertificateType.profileID, 
	GuaranteeCertificateType.profileExecutionID, 
	GuaranteeCertificateType.iD, GuaranteeCertificateType.copyIndicator, 
	GuaranteeCertificateType.uUID, 
	GuaranteeCertificateType.contractFolderID, 
	GuaranteeCertificateType.issueDate, 
	GuaranteeCertificateType.issueTime, 
	GuaranteeCertificateType.guaranteeTypeCode, 
	GuaranteeCertificateType.purpose-list.purpose, 
	GuaranteeCertificateType.liabilityAmount, 
	GuaranteeCertificateType.constitutionCode, 
	GuaranteeCertificateType.note-list.note
	AS "urn:oasis:names:specification:ubl:schema:xsd:CommonBasicComponents-2"
	    PREFIX "cbc"
    NAMESPACE GuaranteeCertificateType.applicablePeriod, 
	GuaranteeCertificateType.applicableRegulation-list.applicableRegulation,
	GuaranteeCertificateType.guaranteeDocumentReference-list.guaranteeDocumentReference,
	GuaranteeCertificateType.immobilizedSecurity-list.immobilizedSecurity,
	GuaranteeCertificateType.signature-list.signature, 
	GuaranteeCertificateType.guarantorParty, 
	GuaranteeCertificateType.interestedParty, 
	GuaranteeCertificateType.beneficiaryParty
	AS "urn:oasis:names:specification:ubl:schema:xsd:CommonAggregateComponents-2"
	    PREFIX "cac"
    NAME GuaranteeCertificateType.uBLExtensions, 
	GuaranteeCertificateType.uBLVersionID, 
	GuaranteeCertificateType.customizationID, 
	GuaranteeCertificateType.profileID, 
	GuaranteeCertificateType.profileExecutionID, 
	GuaranteeCertificateType.iD, GuaranteeCertificateType.copyIndicator, 
	GuaranteeCertificateType.uUID, 
	GuaranteeCertificateType.contractFolderID, 
	GuaranteeCertificateType.issueDate, 
	GuaranteeCertificateType.issueTime, 
	GuaranteeCertificateType.guaranteeTypeCode, 
	GuaranteeCertificateType.purpose-list.purpose, 
	GuaranteeCertificateType.liabilityAmount, 
	GuaranteeCertificateType.constitutionCode, 
	GuaranteeCertificateType.note-list.note, 
	GuaranteeCertificateType.applicablePeriod, 
	GuaranteeCertificateType.applicableRegulation-list.applicableRegulation,
	GuaranteeCertificateType.guaranteeDocumentReference-list.guaranteeDocumentReference,
	GuaranteeCertificateType.immobilizedSecurity-list.immobilizedSecurity,
	GuaranteeCertificateType.signature-list.signature, 
	GuaranteeCertificateType.guarantorParty, 
	GuaranteeCertificateType.interestedParty, 
	GuaranteeCertificateType.beneficiaryParty AS CAPITALIZED
    UNTAGGED SEQUENCE OF
END
