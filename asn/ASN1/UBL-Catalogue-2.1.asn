Catalogue-2
DEFINITIONS AUTOMATIC TAGS ::=
BEGIN
IMPORTS 
    UBLExtensions
    FROM CommonExtensionComponents-2
    UBLVersionID, CustomizationID, ProfileID, ProfileExecutionID, ID-1, UUID, 
    ActionCode, Name-1, IssueDate, IssueTime, RevisionDate, RevisionTime, 
    Note, Description, VersionID, PreviousVersionID, LineCountNumeric
    FROM CommonBasicComponents-2
    ValidityPeriod, ReferencedContract, SourceCatalogueReference, 
    DocumentReference, Signature-1, ProviderParty, ReceiverParty, 
    SellerSupplierParty, ContractorCustomerParty, TradingTerms, CatalogueLine
    FROM CommonAggregateComponents-2;

Catalogue ::= CatalogueType

CatalogueType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    uUID       UUID OPTIONAL,
    actionCode ActionCode OPTIONAL,
    name       Name-1 OPTIONAL,
    issueDate  IssueDate,
    issueTime  IssueTime OPTIONAL,
    revisionDate RevisionDate OPTIONAL,
    revisionTime RevisionTime OPTIONAL,
    note-list  SEQUENCE OF note Note,
    description-list SEQUENCE OF description Description,
    versionID  VersionID OPTIONAL,
    previousVersionID PreviousVersionID OPTIONAL,
    lineCountNumeric LineCountNumeric OPTIONAL,
    validityPeriod-list SEQUENCE OF validityPeriod ValidityPeriod,
    referencedContract-list SEQUENCE OF referencedContract ReferencedContract,
    sourceCatalogueReference SourceCatalogueReference OPTIONAL,
    documentReference-list SEQUENCE OF documentReference DocumentReference,
    signature-list SEQUENCE OF signature Signature-1,
    providerParty ProviderParty,
    receiverParty ReceiverParty,
    sellerSupplierParty SellerSupplierParty OPTIONAL,
    contractorCustomerParty ContractorCustomerParty OPTIONAL,
    tradingTerms-list SEQUENCE OF tradingTerms TradingTerms,
    catalogueLine-list SEQUENCE (SIZE(1..MAX)) OF catalogueLine CatalogueLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:Catalogue-2"
	PREFIX "ns5"
    NAMESPACE CatalogueType.uBLExtensions
	AS "urn:oasis:names:specification:ubl:schema:xsd:CommonExtensionComponents-2"
	    PREFIX "ext"
    NAMESPACE CatalogueType.uBLVersionID, CatalogueType.customizationID, 
	CatalogueType.profileID, CatalogueType.profileExecutionID, 
	CatalogueType.iD, CatalogueType.uUID, CatalogueType.actionCode, 
	CatalogueType.name, CatalogueType.issueDate, CatalogueType.issueTime, 
	CatalogueType.revisionDate, CatalogueType.revisionTime, 
	CatalogueType.note-list.note, 
	CatalogueType.description-list.description, CatalogueType.versionID, 
	CatalogueType.previousVersionID, CatalogueType.lineCountNumeric
	AS "urn:oasis:names:specification:ubl:schema:xsd:CommonBasicComponents-2"
	    PREFIX "cbc"
    NAMESPACE CatalogueType.validityPeriod-list.validityPeriod, 
	CatalogueType.referencedContract-list.referencedContract, 
	CatalogueType.sourceCatalogueReference, 
	CatalogueType.documentReference-list.documentReference, 
	CatalogueType.signature-list.signature, CatalogueType.providerParty, 
	CatalogueType.receiverParty, CatalogueType.sellerSupplierParty, 
	CatalogueType.contractorCustomerParty, 
	CatalogueType.tradingTerms-list.tradingTerms, 
	CatalogueType.catalogueLine-list.catalogueLine
	AS "urn:oasis:names:specification:ubl:schema:xsd:CommonAggregateComponents-2"
	    PREFIX "cac"
    NAME CatalogueType.uBLExtensions, CatalogueType.uBLVersionID, 
	CatalogueType.customizationID, CatalogueType.profileID, 
	CatalogueType.profileExecutionID, CatalogueType.iD, 
	CatalogueType.uUID, CatalogueType.actionCode, CatalogueType.name, 
	CatalogueType.issueDate, CatalogueType.issueTime, 
	CatalogueType.revisionDate, CatalogueType.revisionTime, 
	CatalogueType.note-list.note, 
	CatalogueType.description-list.description, CatalogueType.versionID, 
	CatalogueType.previousVersionID, CatalogueType.lineCountNumeric, 
	CatalogueType.validityPeriod-list.validityPeriod, 
	CatalogueType.referencedContract-list.referencedContract, 
	CatalogueType.sourceCatalogueReference, 
	CatalogueType.documentReference-list.documentReference, 
	CatalogueType.signature-list.signature, CatalogueType.providerParty, 
	CatalogueType.receiverParty, CatalogueType.sellerSupplierParty, 
	CatalogueType.contractorCustomerParty, 
	CatalogueType.tradingTerms-list.tradingTerms, 
	CatalogueType.catalogueLine-list.catalogueLine AS CAPITALIZED
    UNTAGGED SEQUENCE OF
END
