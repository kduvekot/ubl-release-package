TransportExecutionStatus-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, ReferenceDate, ReferenceTime, 
    Note, Description, OperationStatusCode, TransportExecutionPlanReferenceID
    FROM CommonBasicComponents-2
    Signature-1, SenderParty, ReceiverParty, TransportStatus
    FROM CommonAggregateComponents-2;

TransportExecutionStatus ::= TransportExecutionStatusType

TransportExecutionStatusType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    issueDate  IssueDate OPTIONAL,
    issueTime  IssueTime OPTIONAL,
    referenceDate ReferenceDate OPTIONAL,
    referenceTime ReferenceTime OPTIONAL,
    note-list  SEQUENCE OF note Note,
    description-list SEQUENCE OF description Description,
    operationStatusCode OperationStatusCode OPTIONAL,
    transportExecutionPlanReferenceID TransportExecutionPlanReferenceID,
    signature-list SEQUENCE OF signature Signature-1,
    senderParty SenderParty OPTIONAL,
    receiverParty ReceiverParty OPTIONAL,
    transportStatus-list SEQUENCE OF transportStatus TransportStatus
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:TransportExecutionStatus-2"
	PREFIX "ns55"
    NAMESPACE TransportExecutionStatusType.uBLExtensions
	AS "urn:oasis:names:specification:ubl:schema:xsd:CommonExtensionComponents-2"
	    PREFIX "ext"
    NAMESPACE TransportExecutionStatusType.uBLVersionID, 
	TransportExecutionStatusType.customizationID, 
	TransportExecutionStatusType.profileID, 
	TransportExecutionStatusType.profileExecutionID, 
	TransportExecutionStatusType.iD, 
	TransportExecutionStatusType.copyIndicator, 
	TransportExecutionStatusType.uUID, 
	TransportExecutionStatusType.issueDate, 
	TransportExecutionStatusType.issueTime, 
	TransportExecutionStatusType.referenceDate, 
	TransportExecutionStatusType.referenceTime, 
	TransportExecutionStatusType.note-list.note, 
	TransportExecutionStatusType.description-list.description, 
	TransportExecutionStatusType.operationStatusCode, 
	TransportExecutionStatusType.transportExecutionPlanReferenceID
	AS "urn:oasis:names:specification:ubl:schema:xsd:CommonBasicComponents-2"
	    PREFIX "cbc"
    NAMESPACE TransportExecutionStatusType.signature-list.signature, 
	TransportExecutionStatusType.senderParty, 
	TransportExecutionStatusType.receiverParty, 
	TransportExecutionStatusType.transportStatus-list.transportStatus
	AS "urn:oasis:names:specification:ubl:schema:xsd:CommonAggregateComponents-2"
	    PREFIX "cac"
    NAME TransportExecutionStatusType.uBLExtensions, 
	TransportExecutionStatusType.uBLVersionID, 
	TransportExecutionStatusType.customizationID, 
	TransportExecutionStatusType.profileID, 
	TransportExecutionStatusType.profileExecutionID, 
	TransportExecutionStatusType.iD, 
	TransportExecutionStatusType.copyIndicator, 
	TransportExecutionStatusType.uUID, 
	TransportExecutionStatusType.issueDate, 
	TransportExecutionStatusType.issueTime, 
	TransportExecutionStatusType.referenceDate, 
	TransportExecutionStatusType.referenceTime, 
	TransportExecutionStatusType.note-list.note, 
	TransportExecutionStatusType.description-list.description, 
	TransportExecutionStatusType.operationStatusCode, 
	TransportExecutionStatusType.transportExecutionPlanReferenceID, 
	TransportExecutionStatusType.signature-list.signature, 
	TransportExecutionStatusType.senderParty, 
	TransportExecutionStatusType.receiverParty, 
	TransportExecutionStatusType.transportStatus-list.transportStatus
	AS CAPITALIZED
    UNTAGGED SEQUENCE OF
END
