TendererQualificationResponse-2
DEFINITIONS AUTOMATIC TAGS ::=
BEGIN
IMPORTS 
    UBLExtensions
    FROM CommonExtensionComponents-2
    UBLVersionID, CustomizationID, ProfileID, ProfileExecutionID, ID-1, 
    CopyIndicator, UUID, ContractFolderID, ContractName, IssueDate, IssueTime,
    Note
    FROM CommonBasicComponents-2
    SenderParty, ReceiverParty, ResolutionDocumentReference, 
    QualificationResolution, AppealTerms, Signature-1
    FROM CommonAggregateComponents-2;

TendererQualificationResponse ::= TendererQualificationResponseType

TendererQualificationResponseType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    contractFolderID ContractFolderID,
    contractName-list SEQUENCE OF contractName ContractName,
    issueDate  IssueDate,
    issueTime  IssueTime OPTIONAL,
    note-list  SEQUENCE OF note Note,
    senderParty SenderParty,
    receiverParty ReceiverParty,
    resolutionDocumentReference ResolutionDocumentReference OPTIONAL,
    qualificationResolution-list SEQUENCE (SIZE(1..MAX)) OF 
	qualificationResolution QualificationResolution,
    appealTerms AppealTerms OPTIONAL,
    signature-list SEQUENCE OF signature Signature-1
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:TendererQualificationResponse-2"
	PREFIX "ns52"
    NAMESPACE TendererQualificationResponseType.uBLExtensions
	AS "urn:oasis:names:specification:ubl:schema:xsd:CommonExtensionComponents-2"
	    PREFIX "ext"
    NAMESPACE TendererQualificationResponseType.uBLVersionID, 
	TendererQualificationResponseType.customizationID, 
	TendererQualificationResponseType.profileID, 
	TendererQualificationResponseType.profileExecutionID, 
	TendererQualificationResponseType.iD, 
	TendererQualificationResponseType.copyIndicator, 
	TendererQualificationResponseType.uUID, 
	TendererQualificationResponseType.contractFolderID, 
	TendererQualificationResponseType.contractName-list.contractName, 
	TendererQualificationResponseType.issueDate, 
	TendererQualificationResponseType.issueTime, 
	TendererQualificationResponseType.note-list.note
	AS "urn:oasis:names:specification:ubl:schema:xsd:CommonBasicComponents-2"
	    PREFIX "cbc"
    NAMESPACE TendererQualificationResponseType.senderParty, 
	TendererQualificationResponseType.receiverParty, 
	TendererQualificationResponseType.resolutionDocumentReference, 
	TendererQualificationResponseType.qualificationResolution-list.qualificationResolution,
	TendererQualificationResponseType.appealTerms, 
	TendererQualificationResponseType.signature-list.signature
	AS "urn:oasis:names:specification:ubl:schema:xsd:CommonAggregateComponents-2"
	    PREFIX "cac"
    NAME TendererQualificationResponseType.uBLExtensions, 
	TendererQualificationResponseType.uBLVersionID, 
	TendererQualificationResponseType.customizationID, 
	TendererQualificationResponseType.profileID, 
	TendererQualificationResponseType.profileExecutionID, 
	TendererQualificationResponseType.iD, 
	TendererQualificationResponseType.copyIndicator, 
	TendererQualificationResponseType.uUID, 
	TendererQualificationResponseType.contractFolderID, 
	TendererQualificationResponseType.contractName-list.contractName, 
	TendererQualificationResponseType.issueDate, 
	TendererQualificationResponseType.issueTime, 
	TendererQualificationResponseType.note-list.note, 
	TendererQualificationResponseType.senderParty, 
	TendererQualificationResponseType.receiverParty, 
	TendererQualificationResponseType.resolutionDocumentReference, 
	TendererQualificationResponseType.qualificationResolution-list.qualificationResolution,
	TendererQualificationResponseType.appealTerms, 
	TendererQualificationResponseType.signature-list.signature
	AS CAPITALIZED
    UNTAGGED SEQUENCE OF
END
