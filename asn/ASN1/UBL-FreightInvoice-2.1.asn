FreightInvoice-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, InvoiceTypeCode, Note, 
    TaxPointDate, DocumentCurrencyCode, TaxCurrencyCode, PricingCurrencyCode, 
    PaymentCurrencyCode, PaymentAlternativeCurrencyCode, AccountingCostCode, 
    AccountingCost, LineCountNumeric
    FROM CommonBasicComponents-2
    InvoicePeriod, Shipment, OrderReference, BillingReference, 
    DespatchDocumentReference, ReceiptDocumentReference, 
    OriginatorDocumentReference, ContractDocumentReference, 
    AdditionalDocumentReference, Signature-1, AccountingSupplierParty, 
    AccountingCustomerParty, PayeeParty, TaxRepresentativeParty, PaymentMeans,
    PaymentTerms, PrepaidPayment, AllowanceCharge, TaxExchangeRate, 
    PricingExchangeRate, PaymentExchangeRate, PaymentAlternativeExchangeRate, 
    TaxTotal, LegalMonetaryTotal, InvoiceLine
    FROM CommonAggregateComponents-2;

FreightInvoice ::= FreightInvoiceType

FreightInvoiceType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    invoiceTypeCode InvoiceTypeCode OPTIONAL,
    note-list  SEQUENCE OF note Note,
    taxPointDate TaxPointDate OPTIONAL,
    documentCurrencyCode DocumentCurrencyCode OPTIONAL,
    taxCurrencyCode TaxCurrencyCode OPTIONAL,
    pricingCurrencyCode PricingCurrencyCode OPTIONAL,
    paymentCurrencyCode PaymentCurrencyCode OPTIONAL,
    paymentAlternativeCurrencyCode PaymentAlternativeCurrencyCode OPTIONAL,
    accountingCostCode AccountingCostCode OPTIONAL,
    accountingCost AccountingCost OPTIONAL,
    lineCountNumeric LineCountNumeric OPTIONAL,
    invoicePeriod-list SEQUENCE OF invoicePeriod InvoicePeriod,
    shipment   Shipment,
    orderReference OrderReference OPTIONAL,
    billingReference-list SEQUENCE OF billingReference BillingReference,
    despatchDocumentReference-list SEQUENCE OF despatchDocumentReference 
	DespatchDocumentReference,
    receiptDocumentReference-list SEQUENCE OF receiptDocumentReference 
	ReceiptDocumentReference,
    originatorDocumentReference-list SEQUENCE OF originatorDocumentReference 
	OriginatorDocumentReference,
    contractDocumentReference-list SEQUENCE OF contractDocumentReference 
	ContractDocumentReference,
    additionalDocumentReference-list SEQUENCE OF additionalDocumentReference 
	AdditionalDocumentReference,
    signature-list SEQUENCE OF signature Signature-1,
    accountingSupplierParty AccountingSupplierParty,
    accountingCustomerParty AccountingCustomerParty,
    payeeParty PayeeParty OPTIONAL,
    taxRepresentativeParty TaxRepresentativeParty OPTIONAL,
    paymentMeans-list SEQUENCE OF paymentMeans PaymentMeans,
    paymentTerms-list SEQUENCE OF paymentTerms PaymentTerms,
    prepaidPayment-list SEQUENCE OF prepaidPayment PrepaidPayment,
    allowanceCharge-list SEQUENCE OF allowanceCharge AllowanceCharge,
    taxExchangeRate TaxExchangeRate OPTIONAL,
    pricingExchangeRate PricingExchangeRate OPTIONAL,
    paymentExchangeRate PaymentExchangeRate OPTIONAL,
    paymentAlternativeExchangeRate PaymentAlternativeExchangeRate OPTIONAL,
    taxTotal-list SEQUENCE OF taxTotal TaxTotal,
    legalMonetaryTotal LegalMonetaryTotal,
    invoiceLine-list SEQUENCE (SIZE(1..MAX)) OF invoiceLine InvoiceLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:FreightInvoice-2"
	PREFIX "ns23"
    NAMESPACE FreightInvoiceType.uBLExtensions
	AS "urn:oasis:names:specification:ubl:schema:xsd:CommonExtensionComponents-2"
	    PREFIX "ext"
    NAMESPACE FreightInvoiceType.uBLVersionID, 
	FreightInvoiceType.customizationID, FreightInvoiceType.profileID, 
	FreightInvoiceType.profileExecutionID, FreightInvoiceType.iD, 
	FreightInvoiceType.copyIndicator, FreightInvoiceType.uUID, 
	FreightInvoiceType.issueDate, FreightInvoiceType.issueTime, 
	FreightInvoiceType.invoiceTypeCode, FreightInvoiceType.note-list.note,
	FreightInvoiceType.taxPointDate, 
	FreightInvoiceType.documentCurrencyCode, 
	FreightInvoiceType.taxCurrencyCode, 
	FreightInvoiceType.pricingCurrencyCode, 
	FreightInvoiceType.paymentCurrencyCode, 
	FreightInvoiceType.paymentAlternativeCurrencyCode, 
	FreightInvoiceType.accountingCostCode, 
	FreightInvoiceType.accountingCost, FreightInvoiceType.lineCountNumeric
	AS "urn:oasis:names:specification:ubl:schema:xsd:CommonBasicComponents-2"
	    PREFIX "cbc"
    NAMESPACE FreightInvoiceType.invoicePeriod-list.invoicePeriod, 
	FreightInvoiceType.shipment, FreightInvoiceType.orderReference, 
	FreightInvoiceType.billingReference-list.billingReference, 
	FreightInvoiceType.despatchDocumentReference-list.despatchDocumentReference,
	FreightInvoiceType.receiptDocumentReference-list.receiptDocumentReference,
	FreightInvoiceType.originatorDocumentReference-list.originatorDocumentReference,
	FreightInvoiceType.contractDocumentReference-list.contractDocumentReference,
	FreightInvoiceType.additionalDocumentReference-list.additionalDocumentReference,
	FreightInvoiceType.signature-list.signature, 
	FreightInvoiceType.accountingSupplierParty, 
	FreightInvoiceType.accountingCustomerParty, 
	FreightInvoiceType.payeeParty, 
	FreightInvoiceType.taxRepresentativeParty, 
	FreightInvoiceType.paymentMeans-list.paymentMeans, 
	FreightInvoiceType.paymentTerms-list.paymentTerms, 
	FreightInvoiceType.prepaidPayment-list.prepaidPayment, 
	FreightInvoiceType.allowanceCharge-list.allowanceCharge, 
	FreightInvoiceType.taxExchangeRate, 
	FreightInvoiceType.pricingExchangeRate, 
	FreightInvoiceType.paymentExchangeRate, 
	FreightInvoiceType.paymentAlternativeExchangeRate, 
	FreightInvoiceType.taxTotal-list.taxTotal, 
	FreightInvoiceType.legalMonetaryTotal, 
	FreightInvoiceType.invoiceLine-list.invoiceLine
	AS "urn:oasis:names:specification:ubl:schema:xsd:CommonAggregateComponents-2"
	    PREFIX "cac"
    NAME FreightInvoiceType.uBLExtensions, FreightInvoiceType.uBLVersionID, 
	FreightInvoiceType.customizationID, FreightInvoiceType.profileID, 
	FreightInvoiceType.profileExecutionID, FreightInvoiceType.iD, 
	FreightInvoiceType.copyIndicator, FreightInvoiceType.uUID, 
	FreightInvoiceType.issueDate, FreightInvoiceType.issueTime, 
	FreightInvoiceType.invoiceTypeCode, FreightInvoiceType.note-list.note,
	FreightInvoiceType.taxPointDate, 
	FreightInvoiceType.documentCurrencyCode, 
	FreightInvoiceType.taxCurrencyCode, 
	FreightInvoiceType.pricingCurrencyCode, 
	FreightInvoiceType.paymentCurrencyCode, 
	FreightInvoiceType.paymentAlternativeCurrencyCode, 
	FreightInvoiceType.accountingCostCode, 
	FreightInvoiceType.accountingCost, 
	FreightInvoiceType.lineCountNumeric, 
	FreightInvoiceType.invoicePeriod-list.invoicePeriod, 
	FreightInvoiceType.shipment, FreightInvoiceType.orderReference, 
	FreightInvoiceType.billingReference-list.billingReference, 
	FreightInvoiceType.despatchDocumentReference-list.despatchDocumentReference,
	FreightInvoiceType.receiptDocumentReference-list.receiptDocumentReference,
	FreightInvoiceType.originatorDocumentReference-list.originatorDocumentReference,
	FreightInvoiceType.contractDocumentReference-list.contractDocumentReference,
	FreightInvoiceType.additionalDocumentReference-list.additionalDocumentReference,
	FreightInvoiceType.signature-list.signature, 
	FreightInvoiceType.accountingSupplierParty, 
	FreightInvoiceType.accountingCustomerParty, 
	FreightInvoiceType.payeeParty, 
	FreightInvoiceType.taxRepresentativeParty, 
	FreightInvoiceType.paymentMeans-list.paymentMeans, 
	FreightInvoiceType.paymentTerms-list.paymentTerms, 
	FreightInvoiceType.prepaidPayment-list.prepaidPayment, 
	FreightInvoiceType.allowanceCharge-list.allowanceCharge, 
	FreightInvoiceType.taxExchangeRate, 
	FreightInvoiceType.pricingExchangeRate, 
	FreightInvoiceType.paymentExchangeRate, 
	FreightInvoiceType.paymentAlternativeExchangeRate, 
	FreightInvoiceType.taxTotal-list.taxTotal, 
	FreightInvoiceType.legalMonetaryTotal, 
	FreightInvoiceType.invoiceLine-list.invoiceLine AS CAPITALIZED
    UNTAGGED SEQUENCE OF
END
