CatalogueDeletion-2
DEFINITIONS AUTOMATIC TAGS ::=
BEGIN
IMPORTS 
    UBLExtensions
    FROM CommonExtensionComponents-2
    UBLVersionID, CustomizationID, ProfileID, ProfileExecutionID, ID-1, UUID, 
    Name-1, IssueDate, IssueTime, EffectiveDate, EffectiveTime, Note, 
    VersionID, Description
    FROM CommonBasicComponents-2
    ValidityPeriod, DeletedCatalogueReference, ReferencedContract, 
    Signature-1, ReceiverParty, ProviderParty, SellerSupplierParty, 
    ContractorCustomerParty
    FROM CommonAggregateComponents-2;

CatalogueDeletion ::= CatalogueDeletionType

CatalogueDeletionType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    uUID       UUID OPTIONAL,
    name       Name-1 OPTIONAL,
    issueDate  IssueDate,
    issueTime  IssueTime OPTIONAL,
    effectiveDate EffectiveDate OPTIONAL,
    effectiveTime EffectiveTime OPTIONAL,
    note-list  SEQUENCE OF note Note,
    versionID  VersionID OPTIONAL,
    description-list SEQUENCE OF description Description,
    validityPeriod-list SEQUENCE OF validityPeriod ValidityPeriod,
    deletedCatalogueReference DeletedCatalogueReference,
    referencedContract-list SEQUENCE OF referencedContract ReferencedContract,
    signature-list SEQUENCE OF signature Signature-1,
    receiverParty ReceiverParty,
    providerParty ProviderParty,
    sellerSupplierParty SellerSupplierParty OPTIONAL,
    contractorCustomerParty ContractorCustomerParty OPTIONAL
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:CatalogueDeletion-2"
	PREFIX "ns6"
    NAMESPACE CatalogueDeletionType.uBLExtensions
	AS "urn:oasis:names:specification:ubl:schema:xsd:CommonExtensionComponents-2"
	    PREFIX "ext"
    NAMESPACE CatalogueDeletionType.uBLVersionID, 
	CatalogueDeletionType.customizationID, 
	CatalogueDeletionType.profileID, 
	CatalogueDeletionType.profileExecutionID, CatalogueDeletionType.iD, 
	CatalogueDeletionType.uUID, CatalogueDeletionType.name, 
	CatalogueDeletionType.issueDate, CatalogueDeletionType.issueTime, 
	CatalogueDeletionType.effectiveDate, 
	CatalogueDeletionType.effectiveTime, 
	CatalogueDeletionType.note-list.note, CatalogueDeletionType.versionID,
	CatalogueDeletionType.description-list.description
	AS "urn:oasis:names:specification:ubl:schema:xsd:CommonBasicComponents-2"
	    PREFIX "cbc"
    NAMESPACE CatalogueDeletionType.validityPeriod-list.validityPeriod, 
	CatalogueDeletionType.deletedCatalogueReference, 
	CatalogueDeletionType.referencedContract-list.referencedContract, 
	CatalogueDeletionType.signature-list.signature, 
	CatalogueDeletionType.receiverParty, 
	CatalogueDeletionType.providerParty, 
	CatalogueDeletionType.sellerSupplierParty, 
	CatalogueDeletionType.contractorCustomerParty
	AS "urn:oasis:names:specification:ubl:schema:xsd:CommonAggregateComponents-2"
	    PREFIX "cac"
    NAME CatalogueDeletionType.uBLExtensions, 
	CatalogueDeletionType.uBLVersionID, 
	CatalogueDeletionType.customizationID, 
	CatalogueDeletionType.profileID, 
	CatalogueDeletionType.profileExecutionID, CatalogueDeletionType.iD, 
	CatalogueDeletionType.uUID, CatalogueDeletionType.name, 
	CatalogueDeletionType.issueDate, CatalogueDeletionType.issueTime, 
	CatalogueDeletionType.effectiveDate, 
	CatalogueDeletionType.effectiveTime, 
	CatalogueDeletionType.note-list.note, CatalogueDeletionType.versionID,
	CatalogueDeletionType.description-list.description, 
	CatalogueDeletionType.validityPeriod-list.validityPeriod, 
	CatalogueDeletionType.deletedCatalogueReference, 
	CatalogueDeletionType.referencedContract-list.referencedContract, 
	CatalogueDeletionType.signature-list.signature, 
	CatalogueDeletionType.receiverParty, 
	CatalogueDeletionType.providerParty, 
	CatalogueDeletionType.sellerSupplierParty, 
	CatalogueDeletionType.contractorCustomerParty AS CAPITALIZED
    UNTAGGED SEQUENCE OF
END
