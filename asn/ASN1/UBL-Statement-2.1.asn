Statement-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, DocumentCurrencyCode, 
    TotalDebitAmount, TotalCreditAmount, TotalBalanceAmount, LineCountNumeric,
    StatementTypeCode
    FROM CommonBasicComponents-2
    StatementPeriod, AdditionalDocumentReference, Signature-1, 
    AccountingSupplierParty, AccountingCustomerParty, BuyerCustomerParty, 
    SellerSupplierParty, OriginatorCustomerParty, PayeeParty, PaymentMeans, 
    PaymentTerms, AllowanceCharge, TaxTotal, StatementLine
    FROM CommonAggregateComponents-2;

Statement ::= StatementType

StatementType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    documentCurrencyCode DocumentCurrencyCode,
    totalDebitAmount TotalDebitAmount OPTIONAL,
    totalCreditAmount TotalCreditAmount OPTIONAL,
    totalBalanceAmount TotalBalanceAmount OPTIONAL,
    lineCountNumeric LineCountNumeric OPTIONAL,
    statementTypeCode StatementTypeCode OPTIONAL,
    statementPeriod StatementPeriod OPTIONAL,
    additionalDocumentReference-list SEQUENCE OF additionalDocumentReference 
	AdditionalDocumentReference,
    signature-list SEQUENCE OF signature Signature-1,
    accountingSupplierParty AccountingSupplierParty,
    accountingCustomerParty AccountingCustomerParty,
    buyerCustomerParty BuyerCustomerParty OPTIONAL,
    sellerSupplierParty SellerSupplierParty OPTIONAL,
    originatorCustomerParty OriginatorCustomerParty OPTIONAL,
    payeeParty PayeeParty OPTIONAL,
    paymentMeans-list SEQUENCE OF paymentMeans PaymentMeans,
    paymentTerms-list SEQUENCE OF paymentTerms PaymentTerms,
    allowanceCharge-list SEQUENCE OF allowanceCharge AllowanceCharge,
    taxTotal-list SEQUENCE OF taxTotal TaxTotal,
    statementLine-list SEQUENCE (SIZE(1..MAX)) OF statementLine StatementLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:Statement-2"
	PREFIX "ns47"
    NAMESPACE StatementType.uBLExtensions
	AS "urn:oasis:names:specification:ubl:schema:xsd:CommonExtensionComponents-2"
	    PREFIX "ext"
    NAMESPACE StatementType.uBLVersionID, StatementType.customizationID, 
	StatementType.profileID, StatementType.profileExecutionID, 
	StatementType.iD, StatementType.copyIndicator, StatementType.uUID, 
	StatementType.issueDate, StatementType.issueTime, 
	StatementType.note-list.note, StatementType.documentCurrencyCode, 
	StatementType.totalDebitAmount, StatementType.totalCreditAmount, 
	StatementType.totalBalanceAmount, StatementType.lineCountNumeric, 
	StatementType.statementTypeCode
	AS "urn:oasis:names:specification:ubl:schema:xsd:CommonBasicComponents-2"
	    PREFIX "cbc"
    NAMESPACE StatementType.statementPeriod, 
	StatementType.additionalDocumentReference-list.additionalDocumentReference,
	StatementType.signature-list.signature, 
	StatementType.accountingSupplierParty, 
	StatementType.accountingCustomerParty, 
	StatementType.buyerCustomerParty, StatementType.sellerSupplierParty, 
	StatementType.originatorCustomerParty, StatementType.payeeParty, 
	StatementType.paymentMeans-list.paymentMeans, 
	StatementType.paymentTerms-list.paymentTerms, 
	StatementType.allowanceCharge-list.allowanceCharge, 
	StatementType.taxTotal-list.taxTotal, 
	StatementType.statementLine-list.statementLine
	AS "urn:oasis:names:specification:ubl:schema:xsd:CommonAggregateComponents-2"
	    PREFIX "cac"
    NAME StatementType.uBLExtensions, StatementType.uBLVersionID, 
	StatementType.customizationID, StatementType.profileID, 
	StatementType.profileExecutionID, StatementType.iD, 
	StatementType.copyIndicator, StatementType.uUID, 
	StatementType.issueDate, StatementType.issueTime, 
	StatementType.note-list.note, StatementType.documentCurrencyCode, 
	StatementType.totalDebitAmount, StatementType.totalCreditAmount, 
	StatementType.totalBalanceAmount, StatementType.lineCountNumeric, 
	StatementType.statementTypeCode, StatementType.statementPeriod, 
	StatementType.additionalDocumentReference-list.additionalDocumentReference,
	StatementType.signature-list.signature, 
	StatementType.accountingSupplierParty, 
	StatementType.accountingCustomerParty, 
	StatementType.buyerCustomerParty, StatementType.sellerSupplierParty, 
	StatementType.originatorCustomerParty, StatementType.payeeParty, 
	StatementType.paymentMeans-list.paymentMeans, 
	StatementType.paymentTerms-list.paymentTerms, 
	StatementType.allowanceCharge-list.allowanceCharge, 
	StatementType.taxTotal-list.taxTotal, 
	StatementType.statementLine-list.statementLine AS CAPITALIZED
    UNTAGGED SEQUENCE OF
END
