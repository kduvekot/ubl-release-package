CreditNote-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, TaxPointDate, Note, 
    DocumentCurrencyCode, TaxCurrencyCode, PricingCurrencyCode, 
    PaymentCurrencyCode, PaymentAlternativeCurrencyCode, AccountingCostCode, 
    AccountingCost, LineCountNumeric
    FROM CommonBasicComponents-2
    InvoicePeriod, DiscrepancyResponse, OrderReference, BillingReference, 
    DespatchDocumentReference, ReceiptDocumentReference, 
    ContractDocumentReference, AdditionalDocumentReference, 
    StatementDocumentReference, OriginatorDocumentReference, Signature-1, 
    AccountingSupplierParty, AccountingCustomerParty, PayeeParty, 
    BuyerCustomerParty, SellerSupplierParty, TaxRepresentativeParty, Delivery,
    DeliveryTerms, PaymentMeans, PaymentTerms, TaxExchangeRate, 
    PricingExchangeRate, PaymentExchangeRate, PaymentAlternativeExchangeRate, 
    AllowanceCharge, TaxTotal, LegalMonetaryTotal, CreditNoteLine
    FROM CommonAggregateComponents-2;

CreditNote ::= CreditNoteType

CreditNoteType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    taxPointDate TaxPointDate OPTIONAL,
    note-list  SEQUENCE OF note Note,
    documentCurrencyCode DocumentCurrencyCode OPTIONAL,
    taxCurrencyCode TaxCurrencyCode OPTIONAL,
    pricingCurrencyCode PricingCurrencyCode OPTIONAL,
    paymentCurrencyCode PaymentCurrencyCode OPTIONAL,
    paymentAlternativeCurrencyCode PaymentAlternativeCurrencyCode OPTIONAL,
    accountingCostCode AccountingCostCode OPTIONAL,
    accountingCost AccountingCost OPTIONAL,
    lineCountNumeric LineCountNumeric OPTIONAL,
    invoicePeriod-list SEQUENCE OF invoicePeriod InvoicePeriod,
    discrepancyResponse-list SEQUENCE OF discrepancyResponse 
	DiscrepancyResponse,
    orderReference OrderReference OPTIONAL,
    billingReference-list SEQUENCE OF billingReference BillingReference,
    despatchDocumentReference-list SEQUENCE OF despatchDocumentReference 
	DespatchDocumentReference,
    receiptDocumentReference-list SEQUENCE OF receiptDocumentReference 
	ReceiptDocumentReference,
    contractDocumentReference-list SEQUENCE OF contractDocumentReference 
	ContractDocumentReference,
    additionalDocumentReference-list SEQUENCE OF additionalDocumentReference 
	AdditionalDocumentReference,
    statementDocumentReference-list SEQUENCE OF statementDocumentReference 
	StatementDocumentReference,
    originatorDocumentReference-list SEQUENCE OF originatorDocumentReference 
	OriginatorDocumentReference,
    signature-list SEQUENCE OF signature Signature-1,
    accountingSupplierParty AccountingSupplierParty,
    accountingCustomerParty AccountingCustomerParty,
    payeeParty PayeeParty OPTIONAL,
    buyerCustomerParty BuyerCustomerParty OPTIONAL,
    sellerSupplierParty SellerSupplierParty OPTIONAL,
    taxRepresentativeParty TaxRepresentativeParty OPTIONAL,
    delivery-list SEQUENCE OF delivery Delivery,
    deliveryTerms-list SEQUENCE OF deliveryTerms DeliveryTerms,
    paymentMeans-list SEQUENCE OF paymentMeans PaymentMeans,
    paymentTerms-list SEQUENCE OF paymentTerms PaymentTerms,
    taxExchangeRate TaxExchangeRate OPTIONAL,
    pricingExchangeRate PricingExchangeRate OPTIONAL,
    paymentExchangeRate PaymentExchangeRate OPTIONAL,
    paymentAlternativeExchangeRate PaymentAlternativeExchangeRate OPTIONAL,
    allowanceCharge-list SEQUENCE OF allowanceCharge AllowanceCharge,
    taxTotal-list SEQUENCE OF taxTotal TaxTotal,
    legalMonetaryTotal LegalMonetaryTotal,
    creditNoteLine-list SEQUENCE (SIZE(1..MAX)) OF creditNoteLine 
	CreditNoteLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:CreditNote-2"
	PREFIX "ns13"
    NAMESPACE CreditNoteType.uBLExtensions
	AS "urn:oasis:names:specification:ubl:schema:xsd:CommonExtensionComponents-2"
	    PREFIX "ext"
    NAMESPACE CreditNoteType.uBLVersionID, CreditNoteType.customizationID, 
	CreditNoteType.profileID, CreditNoteType.profileExecutionID, 
	CreditNoteType.iD, CreditNoteType.copyIndicator, CreditNoteType.uUID, 
	CreditNoteType.issueDate, CreditNoteType.issueTime, 
	CreditNoteType.taxPointDate, CreditNoteType.note-list.note, 
	CreditNoteType.documentCurrencyCode, CreditNoteType.taxCurrencyCode, 
	CreditNoteType.pricingCurrencyCode, 
	CreditNoteType.paymentCurrencyCode, 
	CreditNoteType.paymentAlternativeCurrencyCode, 
	CreditNoteType.accountingCostCode, CreditNoteType.accountingCost, 
	CreditNoteType.lineCountNumeric
	AS "urn:oasis:names:specification:ubl:schema:xsd:CommonBasicComponents-2"
	    PREFIX "cbc"
    NAMESPACE CreditNoteType.invoicePeriod-list.invoicePeriod, 
	CreditNoteType.discrepancyResponse-list.discrepancyResponse, 
	CreditNoteType.orderReference, 
	CreditNoteType.billingReference-list.billingReference, 
	CreditNoteType.despatchDocumentReference-list.despatchDocumentReference,
	CreditNoteType.receiptDocumentReference-list.receiptDocumentReference,
	CreditNoteType.contractDocumentReference-list.contractDocumentReference,
	CreditNoteType.additionalDocumentReference-list.additionalDocumentReference,
	CreditNoteType.statementDocumentReference-list.statementDocumentReference,
	CreditNoteType.originatorDocumentReference-list.originatorDocumentReference,
	CreditNoteType.signature-list.signature, 
	CreditNoteType.accountingSupplierParty, 
	CreditNoteType.accountingCustomerParty, CreditNoteType.payeeParty, 
	CreditNoteType.buyerCustomerParty, CreditNoteType.sellerSupplierParty,
	CreditNoteType.taxRepresentativeParty, 
	CreditNoteType.delivery-list.delivery, 
	CreditNoteType.deliveryTerms-list.deliveryTerms, 
	CreditNoteType.paymentMeans-list.paymentMeans, 
	CreditNoteType.paymentTerms-list.paymentTerms, 
	CreditNoteType.taxExchangeRate, CreditNoteType.pricingExchangeRate, 
	CreditNoteType.paymentExchangeRate, 
	CreditNoteType.paymentAlternativeExchangeRate, 
	CreditNoteType.allowanceCharge-list.allowanceCharge, 
	CreditNoteType.taxTotal-list.taxTotal, 
	CreditNoteType.legalMonetaryTotal, 
	CreditNoteType.creditNoteLine-list.creditNoteLine
	AS "urn:oasis:names:specification:ubl:schema:xsd:CommonAggregateComponents-2"
	    PREFIX "cac"
    NAME CreditNoteType.uBLExtensions, CreditNoteType.uBLVersionID, 
	CreditNoteType.customizationID, CreditNoteType.profileID, 
	CreditNoteType.profileExecutionID, CreditNoteType.iD, 
	CreditNoteType.copyIndicator, CreditNoteType.uUID, 
	CreditNoteType.issueDate, CreditNoteType.issueTime, 
	CreditNoteType.taxPointDate, CreditNoteType.note-list.note, 
	CreditNoteType.documentCurrencyCode, CreditNoteType.taxCurrencyCode, 
	CreditNoteType.pricingCurrencyCode, 
	CreditNoteType.paymentCurrencyCode, 
	CreditNoteType.paymentAlternativeCurrencyCode, 
	CreditNoteType.accountingCostCode, CreditNoteType.accountingCost, 
	CreditNoteType.lineCountNumeric, 
	CreditNoteType.invoicePeriod-list.invoicePeriod, 
	CreditNoteType.discrepancyResponse-list.discrepancyResponse, 
	CreditNoteType.orderReference, 
	CreditNoteType.billingReference-list.billingReference, 
	CreditNoteType.despatchDocumentReference-list.despatchDocumentReference,
	CreditNoteType.receiptDocumentReference-list.receiptDocumentReference,
	CreditNoteType.contractDocumentReference-list.contractDocumentReference,
	CreditNoteType.additionalDocumentReference-list.additionalDocumentReference,
	CreditNoteType.statementDocumentReference-list.statementDocumentReference,
	CreditNoteType.originatorDocumentReference-list.originatorDocumentReference,
	CreditNoteType.signature-list.signature, 
	CreditNoteType.accountingSupplierParty, 
	CreditNoteType.accountingCustomerParty, CreditNoteType.payeeParty, 
	CreditNoteType.buyerCustomerParty, CreditNoteType.sellerSupplierParty,
	CreditNoteType.taxRepresentativeParty, 
	CreditNoteType.delivery-list.delivery, 
	CreditNoteType.deliveryTerms-list.deliveryTerms, 
	CreditNoteType.paymentMeans-list.paymentMeans, 
	CreditNoteType.paymentTerms-list.paymentTerms, 
	CreditNoteType.taxExchangeRate, CreditNoteType.pricingExchangeRate, 
	CreditNoteType.paymentExchangeRate, 
	CreditNoteType.paymentAlternativeExchangeRate, 
	CreditNoteType.allowanceCharge-list.allowanceCharge, 
	CreditNoteType.taxTotal-list.taxTotal, 
	CreditNoteType.legalMonetaryTotal, 
	CreditNoteType.creditNoteLine-list.creditNoteLine AS CAPITALIZED
    UNTAGGED SEQUENCE OF
END
