ReceiptAdvice-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, DocumentStatusCode, Note, 
    LineCountNumeric
    FROM CommonBasicComponents-2
    OrderReference, DespatchDocumentReference, AdditionalDocumentReference, 
    Signature-1, DeliveryCustomerParty, DespatchSupplierParty, 
    BuyerCustomerParty, SellerSupplierParty, Shipment, ReceiptLine
    FROM CommonAggregateComponents-2;

ReceiptAdvice ::= ReceiptAdviceType

ReceiptAdviceType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    documentStatusCode DocumentStatusCode OPTIONAL,
    note-list  SEQUENCE OF note Note,
    lineCountNumeric LineCountNumeric OPTIONAL,
    orderReference-list SEQUENCE OF orderReference OrderReference,
    despatchDocumentReference-list SEQUENCE OF despatchDocumentReference 
	DespatchDocumentReference,
    additionalDocumentReference-list SEQUENCE OF additionalDocumentReference 
	AdditionalDocumentReference,
    signature-list SEQUENCE OF signature Signature-1,
    deliveryCustomerParty DeliveryCustomerParty,
    despatchSupplierParty DespatchSupplierParty,
    buyerCustomerParty BuyerCustomerParty OPTIONAL,
    sellerSupplierParty SellerSupplierParty OPTIONAL,
    shipment   Shipment OPTIONAL,
    receiptLine-list SEQUENCE (SIZE(1..MAX)) OF receiptLine ReceiptLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:ReceiptAdvice-2"
	PREFIX "ns40"
    NAMESPACE ReceiptAdviceType.uBLExtensions
	AS "urn:oasis:names:specification:ubl:schema:xsd:CommonExtensionComponents-2"
	    PREFIX "ext"
    NAMESPACE ReceiptAdviceType.uBLVersionID, 
	ReceiptAdviceType.customizationID, ReceiptAdviceType.profileID, 
	ReceiptAdviceType.profileExecutionID, ReceiptAdviceType.iD, 
	ReceiptAdviceType.copyIndicator, ReceiptAdviceType.uUID, 
	ReceiptAdviceType.issueDate, ReceiptAdviceType.issueTime, 
	ReceiptAdviceType.documentStatusCode, 
	ReceiptAdviceType.note-list.note, ReceiptAdviceType.lineCountNumeric
	AS "urn:oasis:names:specification:ubl:schema:xsd:CommonBasicComponents-2"
	    PREFIX "cbc"
    NAMESPACE ReceiptAdviceType.orderReference-list.orderReference, 
	ReceiptAdviceType.despatchDocumentReference-list.despatchDocumentReference,
	ReceiptAdviceType.additionalDocumentReference-list.additionalDocumentReference,
	ReceiptAdviceType.signature-list.signature, 
	ReceiptAdviceType.deliveryCustomerParty, 
	ReceiptAdviceType.despatchSupplierParty, 
	ReceiptAdviceType.buyerCustomerParty, 
	ReceiptAdviceType.sellerSupplierParty, ReceiptAdviceType.shipment, 
	ReceiptAdviceType.receiptLine-list.receiptLine
	AS "urn:oasis:names:specification:ubl:schema:xsd:CommonAggregateComponents-2"
	    PREFIX "cac"
    NAME ReceiptAdviceType.uBLExtensions, ReceiptAdviceType.uBLVersionID, 
	ReceiptAdviceType.customizationID, ReceiptAdviceType.profileID, 
	ReceiptAdviceType.profileExecutionID, ReceiptAdviceType.iD, 
	ReceiptAdviceType.copyIndicator, ReceiptAdviceType.uUID, 
	ReceiptAdviceType.issueDate, ReceiptAdviceType.issueTime, 
	ReceiptAdviceType.documentStatusCode, 
	ReceiptAdviceType.note-list.note, ReceiptAdviceType.lineCountNumeric, 
	ReceiptAdviceType.orderReference-list.orderReference, 
	ReceiptAdviceType.despatchDocumentReference-list.despatchDocumentReference,
	ReceiptAdviceType.additionalDocumentReference-list.additionalDocumentReference,
	ReceiptAdviceType.signature-list.signature, 
	ReceiptAdviceType.deliveryCustomerParty, 
	ReceiptAdviceType.despatchSupplierParty, 
	ReceiptAdviceType.buyerCustomerParty, 
	ReceiptAdviceType.sellerSupplierParty, ReceiptAdviceType.shipment, 
	ReceiptAdviceType.receiptLine-list.receiptLine AS CAPITALIZED
    UNTAGGED SEQUENCE OF
END
