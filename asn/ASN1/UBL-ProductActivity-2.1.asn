ProductActivity-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, DocumentCurrencyCode
    FROM CommonBasicComponents-2
    ActivityPeriod, DocumentReference, Signature-1, SenderParty, 
    ReceiverParty, SupplyChainActivityDataLine
    FROM CommonAggregateComponents-2;

ProductActivity ::= ProductActivityType

ProductActivityType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    documentCurrencyCode DocumentCurrencyCode OPTIONAL,
    activityPeriod ActivityPeriod,
    documentReference-list SEQUENCE OF documentReference DocumentReference,
    signature-list SEQUENCE OF signature Signature-1,
    senderParty SenderParty,
    receiverParty ReceiverParty,
    supplyChainActivityDataLine-list SEQUENCE (SIZE(1..MAX)) OF 
	supplyChainActivityDataLine SupplyChainActivityDataLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:ProductActivity-2"
	PREFIX "ns38"
    NAMESPACE ProductActivityType.uBLExtensions
	AS "urn:oasis:names:specification:ubl:schema:xsd:CommonExtensionComponents-2"
	    PREFIX "ext"
    NAMESPACE ProductActivityType.uBLVersionID, 
	ProductActivityType.customizationID, ProductActivityType.profileID, 
	ProductActivityType.profileExecutionID, ProductActivityType.iD, 
	ProductActivityType.copyIndicator, ProductActivityType.uUID, 
	ProductActivityType.issueDate, ProductActivityType.issueTime, 
	ProductActivityType.note-list.note, 
	ProductActivityType.documentCurrencyCode
	AS "urn:oasis:names:specification:ubl:schema:xsd:CommonBasicComponents-2"
	    PREFIX "cbc"
    NAMESPACE ProductActivityType.activityPeriod, 
	ProductActivityType.documentReference-list.documentReference, 
	ProductActivityType.signature-list.signature, 
	ProductActivityType.senderParty, ProductActivityType.receiverParty, 
	ProductActivityType.supplyChainActivityDataLine-list.supplyChainActivityDataLine
	AS "urn:oasis:names:specification:ubl:schema:xsd:CommonAggregateComponents-2"
	    PREFIX "cac"
    NAME ProductActivityType.uBLExtensions, ProductActivityType.uBLVersionID, 
	ProductActivityType.customizationID, ProductActivityType.profileID, 
	ProductActivityType.profileExecutionID, ProductActivityType.iD, 
	ProductActivityType.copyIndicator, ProductActivityType.uUID, 
	ProductActivityType.issueDate, ProductActivityType.issueTime, 
	ProductActivityType.note-list.note, 
	ProductActivityType.documentCurrencyCode, 
	ProductActivityType.activityPeriod, 
	ProductActivityType.documentReference-list.documentReference, 
	ProductActivityType.signature-list.signature, 
	ProductActivityType.senderParty, ProductActivityType.receiverParty, 
	ProductActivityType.supplyChainActivityDataLine-list.supplyChainActivityDataLine
	AS CAPITALIZED
    UNTAGGED SEQUENCE OF
END
