CoreComponentTypeSchemaModule-2
DEFINITIONS AUTOMATIC TAGS ::=
BEGIN
IMPORTS 
    NormalizedString, Decimal, String, AnyURI, Language
    FROM XSD;

AmountType-2 ::= SEQUENCE {
    currencyCodeListVersionID XSD.NormalizedString OPTIONAL,
    currencyID   XSD.NormalizedString OPTIONAL,
    base         XSD.Decimal
}

BinaryObjectType-1 ::= SEQUENCE {
    characterSetCode XSD.NormalizedString OPTIONAL,
    encodingCode     XSD.NormalizedString OPTIONAL,
    filename         XSD.String OPTIONAL,
    format           XSD.String OPTIONAL,
    mimeCode         XSD.NormalizedString OPTIONAL,
    uri              XSD.AnyURI OPTIONAL,
    base             OCTET STRING
}

CodeType-1 ::= SEQUENCE {
    languageID     XSD.Language OPTIONAL,
    listAgencyID   XSD.NormalizedString OPTIONAL,
    listAgencyName XSD.String OPTIONAL,
    listID         XSD.NormalizedString OPTIONAL,
    listName       XSD.String OPTIONAL,
    listSchemeURI  XSD.AnyURI OPTIONAL,
    listURI        XSD.AnyURI OPTIONAL,
    listVersionID  XSD.NormalizedString OPTIONAL,
    name           XSD.String OPTIONAL,
    base           XSD.NormalizedString
}

DateTimeType-1 ::= SEQUENCE {
    format XSD.String OPTIONAL,
    base   XSD.String
}

IdentifierType-2 ::= SEQUENCE {
    schemeAgencyID   XSD.NormalizedString OPTIONAL,
    schemeAgencyName XSD.String OPTIONAL,
    schemeDataURI    XSD.AnyURI OPTIONAL,
    schemeID         XSD.NormalizedString OPTIONAL,
    schemeName       XSD.String OPTIONAL,
    schemeURI        XSD.AnyURI OPTIONAL,
    schemeVersionID  XSD.NormalizedString OPTIONAL,
    base             XSD.NormalizedString
}

IndicatorType-1 ::= SEQUENCE {
    format XSD.String OPTIONAL,
    base   XSD.String
}

MeasureType-2 ::= SEQUENCE {
    unitCode     XSD.NormalizedString OPTIONAL,
    unitCodeListVersionID XSD.NormalizedString OPTIONAL,
    base         XSD.Decimal
}

NumericType-1 ::= SEQUENCE {
    format XSD.String OPTIONAL,
    base   XSD.Decimal
}

QuantityType-2 ::= SEQUENCE {
    unitCode      XSD.NormalizedString OPTIONAL,
    unitCodeListAgencyID XSD.NormalizedString OPTIONAL,
    unitCodeListAgencyName XSD.String OPTIONAL,
    unitCodeListID XSD.NormalizedString OPTIONAL,
    base          XSD.Decimal
}

TextType-2 ::= SEQUENCE {
    languageID       XSD.Language OPTIONAL,
    languageLocaleID XSD.NormalizedString OPTIONAL,
    base             XSD.String
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:un:unece:uncefact:data:specification:CoreComponentTypeSchemaModule:2"
	PREFIX "ccts-cct"
    NOT NAMESPACE AmountType-2.currencyCodeListVersionID, 
	AmountType-2.currencyID, BinaryObjectType-1.characterSetCode, 
	BinaryObjectType-1.encodingCode, BinaryObjectType-1.filename, 
	BinaryObjectType-1.format, BinaryObjectType-1.mimeCode, 
	BinaryObjectType-1.uri, CodeType-1.languageID, 
	CodeType-1.listAgencyID, CodeType-1.listAgencyName, CodeType-1.listID,
	CodeType-1.listName, CodeType-1.listSchemeURI, CodeType-1.listURI, 
	CodeType-1.listVersionID, CodeType-1.name, DateTimeType-1.format, 
	IdentifierType-2.schemeAgencyID, IdentifierType-2.schemeAgencyName, 
	IdentifierType-2.schemeDataURI, IdentifierType-2.schemeID, 
	IdentifierType-2.schemeName, IdentifierType-2.schemeURI, 
	IdentifierType-2.schemeVersionID, IndicatorType-1.format, 
	MeasureType-2.unitCode, MeasureType-2.unitCodeListVersionID, 
	NumericType-1.format, QuantityType-2.unitCode, 
	QuantityType-2.unitCodeListAgencyID, 
	QuantityType-2.unitCodeListAgencyName, QuantityType-2.unitCodeListID, 
	TextType-2.languageID, TextType-2.languageLocaleID
    NAME AmountType-2 AS "AmountType"
    NAME BinaryObjectType-1 AS "BinaryObjectType"
    NAME CodeType-1 AS "CodeType"
    NAME DateTimeType-1 AS "DateTimeType"
    NAME IdentifierType-2 AS "IdentifierType"
    NAME IndicatorType-1 AS "IndicatorType"
    NAME MeasureType-2 AS "MeasureType"
    NAME NumericType-1 AS "NumericType"
    NAME QuantityType-2 AS "QuantityType"
    NAME TextType-2 AS "TextType"
    ATTRIBUTE AmountType-2.currencyCodeListVersionID, AmountType-2.currencyID,
	DateTimeType-1.format, IndicatorType-1.format, MeasureType-2.unitCode,
	MeasureType-2.unitCodeListVersionID, NumericType-1.format, 
	TextType-2.languageID, TextType-2.languageLocaleID
    ATTRIBUTE ALL IN BinaryObjectType-1, ALL IN CodeType-1, 
	ALL IN IdentifierType-2, ALL IN QuantityType-2
    NOT ATTRIBUTE BinaryObjectType-1.base, CodeType-1.base, 
	IdentifierType-2.base, QuantityType-2.base
    BASE64 BinaryObjectType-1.base
    UNTAGGED base IN ALL
END
