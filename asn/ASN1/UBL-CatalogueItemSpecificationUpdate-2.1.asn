CatalogueItemSpecificationUpdate-2
DEFINITIONS AUTOMATIC TAGS ::=
BEGIN
IMPORTS 
    UBLExtensions
    FROM CommonExtensionComponents-2
    UBLVersionID, CustomizationID, ProfileID, ProfileExecutionID, ID-1, UUID, 
    Name-1, IssueDate, IssueTime, RevisionDate, RevisionTime, Note, 
    Description, VersionID, LineCountNumeric
    FROM CommonBasicComponents-2
    ValidityPeriod, RelatedCatalogueReference, ReferencedContract, 
    Signature-1, ProviderParty, ReceiverParty, SellerSupplierParty, 
    ContractorCustomerParty, TradingTerms, DefaultLanguage, 
    CatalogueItemSpecificationUpdateLine
    FROM CommonAggregateComponents-2;

CatalogueItemSpecificationUpdate ::= CatalogueItemSpecificationUpdateType

CatalogueItemSpecificationUpdateType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    uUID       UUID OPTIONAL,
    name       Name-1 OPTIONAL,
    issueDate  IssueDate,
    issueTime  IssueTime OPTIONAL,
    revisionDate RevisionDate OPTIONAL,
    revisionTime RevisionTime OPTIONAL,
    note-list  SEQUENCE OF note Note,
    description-list SEQUENCE OF description Description,
    versionID  VersionID OPTIONAL,
    lineCountNumeric LineCountNumeric OPTIONAL,
    validityPeriod-list SEQUENCE OF validityPeriod ValidityPeriod,
    relatedCatalogueReference RelatedCatalogueReference,
    referencedContract-list SEQUENCE OF referencedContract ReferencedContract,
    signature-list SEQUENCE OF signature Signature-1,
    providerParty ProviderParty,
    receiverParty ReceiverParty,
    sellerSupplierParty SellerSupplierParty OPTIONAL,
    contractorCustomerParty ContractorCustomerParty OPTIONAL,
    tradingTerms TradingTerms OPTIONAL,
    defaultLanguage DefaultLanguage OPTIONAL,
    catalogueItemSpecificationUpdateLine-list SEQUENCE (SIZE(1..MAX)) OF 
	catalogueItemSpecificationUpdateLine 
	CatalogueItemSpecificationUpdateLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:CatalogueItemSpecificationUpdate-2"
	PREFIX "ns7"
    NAMESPACE CatalogueItemSpecificationUpdateType.uBLExtensions
	AS "urn:oasis:names:specification:ubl:schema:xsd:CommonExtensionComponents-2"
	    PREFIX "ext"
    NAMESPACE CatalogueItemSpecificationUpdateType.uBLVersionID, 
	CatalogueItemSpecificationUpdateType.customizationID, 
	CatalogueItemSpecificationUpdateType.profileID, 
	CatalogueItemSpecificationUpdateType.profileExecutionID, 
	CatalogueItemSpecificationUpdateType.iD, 
	CatalogueItemSpecificationUpdateType.uUID, 
	CatalogueItemSpecificationUpdateType.name, 
	CatalogueItemSpecificationUpdateType.issueDate, 
	CatalogueItemSpecificationUpdateType.issueTime, 
	CatalogueItemSpecificationUpdateType.revisionDate, 
	CatalogueItemSpecificationUpdateType.revisionTime, 
	CatalogueItemSpecificationUpdateType.note-list.note, 
	CatalogueItemSpecificationUpdateType.description-list.description, 
	CatalogueItemSpecificationUpdateType.versionID, 
	CatalogueItemSpecificationUpdateType.lineCountNumeric
	AS "urn:oasis:names:specification:ubl:schema:xsd:CommonBasicComponents-2"
	    PREFIX "cbc"
    NAMESPACE CatalogueItemSpecificationUpdateType.validityPeriod-list.validityPeriod,
	CatalogueItemSpecificationUpdateType.relatedCatalogueReference, 
	CatalogueItemSpecificationUpdateType.referencedContract-list.referencedContract,
	CatalogueItemSpecificationUpdateType.signature-list.signature, 
	CatalogueItemSpecificationUpdateType.providerParty, 
	CatalogueItemSpecificationUpdateType.receiverParty, 
	CatalogueItemSpecificationUpdateType.sellerSupplierParty, 
	CatalogueItemSpecificationUpdateType.contractorCustomerParty, 
	CatalogueItemSpecificationUpdateType.tradingTerms, 
	CatalogueItemSpecificationUpdateType.defaultLanguage, 
	CatalogueItemSpecificationUpdateType.catalogueItemSpecificationUpdateLine-list.catalogueItemSpecificationUpdateLine
	AS "urn:oasis:names:specification:ubl:schema:xsd:CommonAggregateComponents-2"
	    PREFIX "cac"
    NAME CatalogueItemSpecificationUpdateType.uBLExtensions, 
	CatalogueItemSpecificationUpdateType.uBLVersionID, 
	CatalogueItemSpecificationUpdateType.customizationID, 
	CatalogueItemSpecificationUpdateType.profileID, 
	CatalogueItemSpecificationUpdateType.profileExecutionID, 
	CatalogueItemSpecificationUpdateType.iD, 
	CatalogueItemSpecificationUpdateType.uUID, 
	CatalogueItemSpecificationUpdateType.name, 
	CatalogueItemSpecificationUpdateType.issueDate, 
	CatalogueItemSpecificationUpdateType.issueTime, 
	CatalogueItemSpecificationUpdateType.revisionDate, 
	CatalogueItemSpecificationUpdateType.revisionTime, 
	CatalogueItemSpecificationUpdateType.note-list.note, 
	CatalogueItemSpecificationUpdateType.description-list.description, 
	CatalogueItemSpecificationUpdateType.versionID, 
	CatalogueItemSpecificationUpdateType.lineCountNumeric, 
	CatalogueItemSpecificationUpdateType.validityPeriod-list.validityPeriod,
	CatalogueItemSpecificationUpdateType.relatedCatalogueReference, 
	CatalogueItemSpecificationUpdateType.referencedContract-list.referencedContract,
	CatalogueItemSpecificationUpdateType.signature-list.signature, 
	CatalogueItemSpecificationUpdateType.providerParty, 
	CatalogueItemSpecificationUpdateType.receiverParty, 
	CatalogueItemSpecificationUpdateType.sellerSupplierParty, 
	CatalogueItemSpecificationUpdateType.contractorCustomerParty, 
	CatalogueItemSpecificationUpdateType.tradingTerms, 
	CatalogueItemSpecificationUpdateType.defaultLanguage, 
	CatalogueItemSpecificationUpdateType.catalogueItemSpecificationUpdateLine-list.catalogueItemSpecificationUpdateLine
	AS CAPITALIZED
    UNTAGGED SEQUENCE OF
END
