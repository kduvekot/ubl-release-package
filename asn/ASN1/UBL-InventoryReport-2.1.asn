InventoryReport-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, Note, DocumentCurrencyCode
    FROM CommonBasicComponents-2
    InventoryPeriod, DocumentReference, Signature-1, RetailerCustomerParty, 
    InventoryReportingParty, SellerSupplierParty, InventoryReportLine
    FROM CommonAggregateComponents-2;

InventoryReport ::= InventoryReportType

InventoryReportType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1,
    copyIndicator CopyIndicator OPTIONAL,
    uUID       UUID OPTIONAL,
    issueDate  IssueDate,
    issueTime  IssueTime OPTIONAL,
    note-list  SEQUENCE OF note Note,
    documentCurrencyCode DocumentCurrencyCode OPTIONAL,
    inventoryPeriod InventoryPeriod OPTIONAL,
    documentReference-list SEQUENCE OF documentReference DocumentReference,
    signature-list SEQUENCE OF signature Signature-1,
    retailerCustomerParty RetailerCustomerParty,
    inventoryReportingParty InventoryReportingParty,
    sellerSupplierParty SellerSupplierParty OPTIONAL,
    inventoryReportLine-list SEQUENCE (SIZE(1..MAX)) OF inventoryReportLine 
	InventoryReportLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL 
	AS "urn:oasis:names:specification:ubl:schema:xsd:InventoryReport-2"
	PREFIX "ns27"
    NAMESPACE InventoryReportType.uBLExtensions
	AS "urn:oasis:names:specification:ubl:schema:xsd:CommonExtensionComponents-2"
	    PREFIX "ext"
    NAMESPACE InventoryReportType.uBLVersionID, 
	InventoryReportType.customizationID, InventoryReportType.profileID, 
	InventoryReportType.profileExecutionID, InventoryReportType.iD, 
	InventoryReportType.copyIndicator, InventoryReportType.uUID, 
	InventoryReportType.issueDate, InventoryReportType.issueTime, 
	InventoryReportType.note-list.note, 
	InventoryReportType.documentCurrencyCode
	AS "urn:oasis:names:specification:ubl:schema:xsd:CommonBasicComponents-2"
	    PREFIX "cbc"
    NAMESPACE InventoryReportType.inventoryPeriod, 
	InventoryReportType.documentReference-list.documentReference, 
	InventoryReportType.signature-list.signature, 
	InventoryReportType.retailerCustomerParty, 
	InventoryReportType.inventoryReportingParty, 
	InventoryReportType.sellerSupplierParty, 
	InventoryReportType.inventoryReportLine-list.inventoryReportLine
	AS "urn:oasis:names:specification:ubl:schema:xsd:CommonAggregateComponents-2"
	    PREFIX "cac"
    NAME InventoryReportType.uBLExtensions, InventoryReportType.uBLVersionID, 
	InventoryReportType.customizationID, InventoryReportType.profileID, 
	InventoryReportType.profileExecutionID, InventoryReportType.iD, 
	InventoryReportType.copyIndicator, InventoryReportType.uUID, 
	InventoryReportType.issueDate, InventoryReportType.issueTime, 
	InventoryReportType.note-list.note, 
	InventoryReportType.documentCurrencyCode, 
	InventoryReportType.inventoryPeriod, 
	InventoryReportType.documentReference-list.documentReference, 
	InventoryReportType.signature-list.signature, 
	InventoryReportType.retailerCustomerParty, 
	InventoryReportType.inventoryReportingParty, 
	InventoryReportType.sellerSupplierParty, 
	InventoryReportType.inventoryReportLine-list.inventoryReportLine
	AS CAPITALIZED
    UNTAGGED SEQUENCE OF
END
