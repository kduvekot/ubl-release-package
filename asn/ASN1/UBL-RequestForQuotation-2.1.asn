RequestForQuotation-2
DEFINITIONS AUTOMATIC TAGS ::=
BEGIN
IMPORTS 
    UBLExtensions
    FROM CommonExtensionComponents-2
    UBLVersionID, CustomizationID, ProfileID, ProfileExecutionID, ID-1, 
    CopyIndicator, UUID, IssueDate, IssueTime, SubmissionDueDate, Note, 
    PricingCurrencyCode, LineCountNumeric
    FROM CommonBasicComponents-2
    RequestedValidityPeriod, CatalogueDocumentReference, 
    AdditionalDocumentReference, Signature-1, OriginatorCustomerParty, 
    SellerSupplierParty, BuyerCustomerParty, Delivery, DeliveryTerms, 
    DestinationCountry, Contract, RequestForQuotationLine
    FROM CommonAggregateComponents-2;

RequestForQuotation ::= RequestForQuotationType

RequestForQuotationType ::= SEQUENCE {
    uBLExtensions UBLExtensions OPTIONAL,
    uBLVersionID UBLVersionID OPTIONAL,
    customizationID CustomizationID OPTIONAL,
    profileID  ProfileID OPTIONAL,
    profileExecutionID ProfileExecutionID OPTIONAL,
    iD         ID-1 OPTIONAL,
    copyIndicator CopyIndicator OPTIONAL,
    uUID       UUID OPTIONAL,
    issueDate  IssueDate,
    issueTime  IssueTime,
    submissionDueDate SubmissionDueDate OPTIONAL,
    note-list  SEQUENCE OF note Note,
    pricingCurrencyCode PricingCurrencyCode OPTIONAL,
    lineCountNumeric LineCountNumeric OPTIONAL,
    requestedValidityPeriod RequestedValidityPeriod OPTIONAL,
    catalogueDocumentReference CatalogueDocumentReference OPTIONAL,
    additionalDocumentReference-list SEQUENCE OF additionalDocumentReference 
	AdditionalDocumentReference,
    signature-list SEQUENCE OF signature Signature-1,
    originatorCustomerParty OriginatorCustomerParty OPTIONAL,
    sellerSupplierParty SellerSupplierParty,
    buyerCustomerParty BuyerCustomerParty OPTIONAL,
    delivery-list SEQUENCE OF delivery Delivery,
    deliveryTerms-list SEQUENCE OF deliveryTerms DeliveryTerms,
    destinationCountry DestinationCountry OPTIONAL,
    contract-list SEQUENCE OF contract Contract,
    requestForQuotationLine-list SEQUENCE (SIZE(1..MAX)) OF 
	requestForQuotationLine RequestForQuotationLine
}

ENCODING-CONTROL XER
    GLOBAL-DEFAULTS MODIFIED-ENCODINGS
    GLOBAL-DEFAULTS CONTROL-NAMESPACE
	"http://www.w3.org/2001/XMLSchema-instance" PREFIX "xsi"
    NAMESPACE ALL, ALL IN ALL AS "urn:oasis:names:specification:ubl:schema:xsd:RequestForQuotation-2"
	PREFIX "ns43"
    NAMESPACE RequestForQuotationType.uBLExtensions
	AS "urn:oasis:names:specification:ubl:schema:xsd:CommonExtensionComponents-2"
	    PREFIX "ext"
    NAMESPACE RequestForQuotationType.uBLVersionID, 
	RequestForQuotationType.customizationID, 
	RequestForQuotationType.profileID, 
	RequestForQuotationType.profileExecutionID, 
	RequestForQuotationType.iD, RequestForQuotationType.copyIndicator, 
	RequestForQuotationType.uUID, RequestForQuotationType.issueDate, 
	RequestForQuotationType.issueTime, 
	RequestForQuotationType.submissionDueDate, 
	RequestForQuotationType.note-list.note, 
	RequestForQuotationType.pricingCurrencyCode, 
	RequestForQuotationType.lineCountNumeric
	AS "urn:oasis:names:specification:ubl:schema:xsd:CommonBasicComponents-2"
	    PREFIX "cbc"
    NAMESPACE RequestForQuotationType.requestedValidityPeriod, 
	RequestForQuotationType.catalogueDocumentReference, 
	RequestForQuotationType.additionalDocumentReference-list.additionalDocumentReference,
	RequestForQuotationType.signature-list.signature, 
	RequestForQuotationType.originatorCustomerParty, 
	RequestForQuotationType.sellerSupplierParty, 
	RequestForQuotationType.buyerCustomerParty, 
	RequestForQuotationType.delivery-list.delivery, 
	RequestForQuotationType.deliveryTerms-list.deliveryTerms, 
	RequestForQuotationType.destinationCountry, 
	RequestForQuotationType.contract-list.contract, 
	RequestForQuotationType.requestForQuotationLine-list.requestForQuotationLine
	AS "urn:oasis:names:specification:ubl:schema:xsd:CommonAggregateComponents-2"
	    PREFIX "cac"
    NAME RequestForQuotationType.uBLExtensions, 
	RequestForQuotationType.uBLVersionID, 
	RequestForQuotationType.customizationID, 
	RequestForQuotationType.profileID, 
	RequestForQuotationType.profileExecutionID, 
	RequestForQuotationType.iD, RequestForQuotationType.copyIndicator, 
	RequestForQuotationType.uUID, RequestForQuotationType.issueDate, 
	RequestForQuotationType.issueTime, 
	RequestForQuotationType.submissionDueDate, 
	RequestForQuotationType.note-list.note, 
	RequestForQuotationType.pricingCurrencyCode, 
	RequestForQuotationType.lineCountNumeric, 
	RequestForQuotationType.requestedValidityPeriod, 
	RequestForQuotationType.catalogueDocumentReference, 
	RequestForQuotationType.additionalDocumentReference-list.additionalDocumentReference,
	RequestForQuotationType.signature-list.signature, 
	RequestForQuotationType.originatorCustomerParty, 
	RequestForQuotationType.sellerSupplierParty, 
	RequestForQuotationType.buyerCustomerParty, 
	RequestForQuotationType.delivery-list.delivery, 
	RequestForQuotationType.deliveryTerms-list.deliveryTerms, 
	RequestForQuotationType.destinationCountry, 
	RequestForQuotationType.contract-list.contract, 
	RequestForQuotationType.requestForQuotationLine-list.requestForQuotationLine
	AS CAPITALIZED
    UNTAGGED SEQUENCE OF
END
